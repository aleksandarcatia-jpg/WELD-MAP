Option Explicit

' ---------------------------------------------------------------------------
' GenerateWeldLabelsFromRegister.CATScript
'
' Drawing macro for Weld Design workflow.
' Reads weld_design_register.csv and tries to update existing Weld Design
' drawing annotations / Weld Symbol.N objects with W001/W002 labels.
'
' It never places random arrows. If a Weld Symbol or position is not accessible,
' the weld is reported as unplaced and processing continues.
' ---------------------------------------------------------------------------

Const MACRO_NAME = "GenerateWeldLabelsFromRegister"
Const REGISTER_FILE_NAME = "weld_design_register.csv"
Const REPORT_FILE_NAME = "weld_labels_from_register_report.txt"
Const SETTINGS_FILE_NAME = "weld_map_settings.ini"

Sub CATMain()
    Dim doc
    Set doc = Nothing

    On Error Resume Next
    Set doc = CATIA.ActiveDocument
    On Error GoTo 0

    If doc Is Nothing Then
        MsgBox "Open CATDrawing and run this macro again.", vbExclamation, MACRO_NAME
        Exit Sub
    End If

    If TypeName(doc) <> "DrawingDocument" Then
        MsgBox "Active document must be CATDrawing.", vbExclamation, MACRO_NAME
        Exit Sub
    End If

    Dim registerPath
    registerPath = ResolveRegisterPath(doc)
    If registerPath = "" Then Exit Sub

    Dim rows
    Set rows = LoadRegisterCsv(registerPath)
    If rows.Count = 0 Then
        MsgBox "No rows found in weld_design_register.csv.", vbExclamation, MACRO_NAME
        Exit Sub
    End If

    Dim report
    Set report = NewList()
    ListAdd report, "Weld labels from register"
    Call AppendRegisterLoadingReport(report, registerPath, rows)
    Call AppendDrawingInventory(doc, report)
    Call AppendSearchInventory(doc, rows, report)
    ListAdd report, ""

    Dim placed
    Dim nativeUpdated
    Dim textFallback
    Dim unplaced
    placed = 0
    nativeUpdated = 0
    textFallback = 0
    unplaced = 0

    Dim i
    Dim rec
    For i = 0 To rows.Count - 1
        Set rec = rows.Item(i)
        ListAdd report, ""
        If PlaceLabelForRecord(doc, rec, report, nativeUpdated, textFallback) Then
            placed = placed + 1
        Else
            unplaced = unplaced + 1
        End If
    Next

    Dim reportFilePath
    reportFilePath = BuildOutputPath(doc, REPORT_FILE_NAME)
    Call WriteTextFile(reportFilePath, report)

    MsgBox "Weld labels from register completed." & vbCrLf & _
           "Weld labels placed: " & CStr(placed) & vbCrLf & _
           "Weld labels updated in native symbol: " & CStr(nativeUpdated) & vbCrLf & _
           "Weld labels placed as text fallback: " & CStr(textFallback) & vbCrLf & _
           "Unplaced weld labels: " & CStr(unplaced) & vbCrLf & _
           "Report: " & reportFilePath, vbInformation, MACRO_NAME
End Sub

Sub AppendRegisterLoadingReport(report, registerPath, rows)
    ListAdd report, ""
    ListAdd report, "=== A) Register loading ==="
    ListAdd report, "Resolved register path: " & CStr(registerPath)
    ListAdd report, "Number of rows: " & CStr(rows.Count)
    ListAdd report, "WeldID list: " & RegisterFieldList(rows, "WeldID")
    ListAdd report, "WeldSymbolName list: " & RegisterFieldList(rows, "WeldSymbolName")
    ListAdd report, "AssemblyJointIndex list: " & RegisterFieldList(rows, "AssemblyJointIndex")
End Sub

Function RegisterFieldList(rows, fieldName)
    Dim textValue
    textValue = ""

    Dim i
    Dim itemValue
    For i = 0 To rows.Count - 1
        itemValue = DictValue(rows.Item(i), fieldName)
        If itemValue <> "" Then
            If textValue <> "" Then textValue = textValue & ", "
            textValue = textValue & itemValue
        End If
    Next

    If textValue = "" Then textValue = "<none>"
    RegisterFieldList = textValue
End Function

Sub AppendDrawingInventory(doc, report)
    ListAdd report, ""
    ListAdd report, "=== B) Drawing sheets/views inventory ==="

    Dim sheets
    Set sheets = Nothing
    On Error Resume Next
    Set sheets = doc.Sheets
    If Err.Number <> 0 Or sheets Is Nothing Then
        ListAdd report, "Sheets: <not accessible>"
        Err.Clear
        On Error GoTo 0
        Exit Sub
    End If
    On Error GoTo 0

    ListAdd report, "Sheets count: " & CStr(SafeCollectionCount(sheets))

    Dim sheetIndex
    Dim viewIndex
    Dim sheetObj
    Dim viewObj
    Dim views

    For sheetIndex = 1 To SafeCollectionCount(sheets)
        Set sheetObj = Nothing
        On Error Resume Next
        Set sheetObj = sheets.Item(sheetIndex)
        If Err.Number <> 0 Or sheetObj Is Nothing Then
            ListAdd report, "Sheet " & CStr(sheetIndex) & ": <not accessible>"
            Err.Clear
            On Error GoTo 0
        Else
            On Error GoTo 0
            Set views = Nothing
            On Error Resume Next
            Set views = sheetObj.Views
            If Err.Number <> 0 Or views Is Nothing Then
                ListAdd report, "Sheet: " & SafeObjectName(sheetObj) & " | Number of views: <not accessible>"
                Err.Clear
                On Error GoTo 0
            Else
                On Error GoTo 0
                ListAdd report, "Sheet: " & SafeObjectName(sheetObj) & " | Number of views: " & CStr(SafeCollectionCount(views))

                For viewIndex = 1 To SafeCollectionCount(views)
                    Set viewObj = Nothing
                    On Error Resume Next
                    Set viewObj = views.Item(viewIndex)
                    If Err.Number <> 0 Or viewObj Is Nothing Then
                        ListAdd report, "  View " & CStr(viewIndex) & ": <not accessible>"
                        Err.Clear
                        On Error GoTo 0
                    Else
                        On Error GoTo 0
                        ListAdd report, "  View: " & SafeObjectName(viewObj)
                        ListAdd report, "    Scale: " & SafeScalarProperty(viewObj, "Scale")
                        ListAdd report, "    X: " & SafeScalarProperty(viewObj, "X")
                        ListAdd report, "    Y: " & SafeScalarProperty(viewObj, "Y")
                        ListAdd report, "    Texts count: " & SafeChildCollectionCount(viewObj, "Texts")
                        ListAdd report, "    Tables count: " & SafeChildCollectionCount(viewObj, "Tables")
                        ListAdd report, "    Generative links: " & ViewGenerativeLinkInfo(viewObj)
                    End If
                Next
            End If
        End If
    Next
End Sub

Sub AppendSearchInventory(doc, rows, report)
    ListAdd report, ""
    ListAdd report, "=== C) Search inventory ==="

    Call AppendSearchQueryReport(doc, report, "Name=*Weld*,all")
    Call AppendSearchQueryReport(doc, report, "Name=*Symbol*,all")
    Call AppendSearchQueryReport(doc, report, "Name=*Annotation*,all")
    Call AppendSearchQueryReport(doc, report, "Type=Annotation,all")
    Call AppendSearchQueryReport(doc, report, "Type=DrawingText,all")

    Dim i
    Dim weldID
    For i = 0 To rows.Count - 1
        weldID = DictValue(rows.Item(i), "WeldID")
        If weldID <> "" Then Call AppendSearchQueryReport(doc, report, "Name=*" & weldID & "*,all")
    Next
End Sub

Sub AppendSearchQueryReport(doc, report, queryText)
    Dim resultCount
    Dim errorText
    Dim firstObj

    Set firstObj = SearchFirstObject(doc, queryText, resultCount, errorText)

    If errorText <> "" Then
        ListAdd report, "Search: " & queryText & " | ERROR: " & errorText
    Else
        ListAdd report, "Search: " & queryText & " | Count: " & CStr(resultCount)
        If Not firstObj Is Nothing Then
            ListAdd report, "  First candidate: " & SafeObjectName(firstObj) & " | TypeName: " & SafeTypeName(firstObj)
        End If
    End If
End Sub

Function PlaceLabelForRecord(doc, rec, report, ByRef nativeUpdated, ByRef textFallback)
    PlaceLabelForRecord = False

    Dim weldID
    Dim symbolName
    Dim jointIndex
    weldID = DictValue(rec, "WeldID")
    symbolName = DictValue(rec, "WeldSymbolName")
    jointIndex = DictValue(rec, "AssemblyJointIndex")

    If weldID = "" Then weldID = "W" & Right("000" & CStr(CLngOrZero(jointIndex)), 3)
    If symbolName = "" And jointIndex <> "" Then symbolName = "Weld Symbol." & CStr(CLngOrZero(jointIndex))

    ListAdd report, "=== " & weldID & " ==="
    ListAdd report, "Register WeldSymbolName: " & EmptyAsText(symbolName)
    ListAdd report, "AssemblyJointIndex: " & EmptyAsText(jointIndex)
    ListAdd report, "Expected symbol names:"
    ListAdd report, "  " & EmptyAsText(symbolName)
    If jointIndex <> "" Then
        ListAdd report, "  Weld Symbol." & CStr(CLngOrZero(jointIndex))
        ListAdd report, "  *Weld Symbol." & CStr(CLngOrZero(jointIndex)) & "*"
        ListAdd report, "  *Weld*" & CStr(CLngOrZero(jointIndex)) & "*"
        ListAdd report, "  *Symbol*" & CStr(CLngOrZero(jointIndex)) & "*"
    End If

    If weldID = "" Or symbolName = "" Then
        ListAdd report, "Search exact result: skipped"
        ListAdd report, "Search wildcard result: skipped"
        ListAdd report, "Candidate object: <none>"
        ListAdd report, "Candidate TypeName: <none>"
        ListAdd report, "Native update attempt: skipped"
        ListAdd report, "Text fallback attempt: skipped"
        ListAdd report, "Reason if failed: missing WeldID or WeldSymbolName"
        ListAdd report, "Final status: UNPLACED"
        Exit Function
    End If

    Dim exactCount
    Dim exactError
    Dim wildcardCount
    Dim wildcardError
    Dim symbolObj
    Set symbolObj = SearchFirstObject(doc, "Name=" & CStr(symbolName) & ",all", exactCount, exactError)
    If exactError <> "" Then
        ListAdd report, "Search exact result: ERROR: " & exactError
    Else
        ListAdd report, "Search exact result: " & CStr(exactCount)
    End If

    If symbolObj Is Nothing Then
        Set symbolObj = SearchFirstObject(doc, "Name=*" & CStr(symbolName) & "*,all", wildcardCount, wildcardError)
    Else
        wildcardCount = 0
        wildcardError = ""
    End If

    If wildcardError <> "" Then
        ListAdd report, "Search wildcard result: ERROR: " & wildcardError
    ElseIf wildcardCount > 0 Then
        ListAdd report, "Search wildcard result: " & CStr(wildcardCount)
    ElseIf exactCount > 0 Then
        ListAdd report, "Search wildcard result: not needed"
    Else
        ListAdd report, "Search wildcard result: 0"
    End If

    If symbolObj Is Nothing And jointIndex <> "" Then
        Set symbolObj = SearchFirstObject(doc, "Name=*Weld*" & CStr(CLngOrZero(jointIndex)) & "*,all", wildcardCount, wildcardError)
        ListAdd report, "Search *Weld*" & CStr(CLngOrZero(jointIndex)) & "* result: " & SearchResultText(wildcardCount, wildcardError)
    End If

    If symbolObj Is Nothing And jointIndex <> "" Then
        Set symbolObj = SearchFirstObject(doc, "Name=*Symbol*" & CStr(CLngOrZero(jointIndex)) & "*,all", wildcardCount, wildcardError)
        ListAdd report, "Search *Symbol*" & CStr(CLngOrZero(jointIndex)) & "* result: " & SearchResultText(wildcardCount, wildcardError)
    End If

    If symbolObj Is Nothing Then
        ListAdd report, "Candidate object: <none>"
        ListAdd report, "Candidate TypeName: <none>"
        ListAdd report, "Native update attempt: skipped"
        ListAdd report, "Text fallback attempt: skipped"
        ListAdd report, "Reason if failed: " & symbolName & " not found in drawing"
        ListAdd report, "Final status: UNPLACED"
        Exit Function
    End If

    ListAdd report, "Candidate object: " & SafeObjectName(symbolObj)
    ListAdd report, "Candidate TypeName: " & SafeTypeName(symbolObj)

    Dim nativeDetail
    If TryUpdateNativeSymbolWithDetail(symbolObj, weldID, nativeDetail) Then
        nativeUpdated = nativeUpdated + 1
        ListAdd report, "Native update attempt: success - " & nativeDetail
        ListAdd report, "Text fallback attempt: not needed"
        ListAdd report, "Reason if failed: <none>"
        ListAdd report, "Final status: PLACED_NATIVE"
        PlaceLabelForRecord = True
        Exit Function
    End If
    ListAdd report, "Native update attempt: failed - " & nativeDetail

    Dim textDetail
    If TryPlaceTextNearSymbolWithDetail(symbolObj, weldID, textDetail) Then
        textFallback = textFallback + 1
        ListAdd report, "Text fallback attempt: success - " & textDetail
        ListAdd report, "Reason if failed: <none>"
        ListAdd report, "Final status: PLACED_TEXT_FALLBACK"
        PlaceLabelForRecord = True
        Exit Function
    End If
    ListAdd report, "Text fallback attempt: failed - " & textDetail

    ListAdd report, "Reason if failed: symbol found but native fields/text position are not accessible"
    ListAdd report, "Final status: UNPLACED"
End Function

Function SearchResultText(resultCount, errorText)
    If CStr(errorText) <> "" Then
        SearchResultText = "ERROR: " & CStr(errorText)
    Else
        SearchResultText = CStr(resultCount)
    End If
End Function

Function SearchFirstObject(doc, queryText, ByRef resultCount, ByRef errorText)
    Set SearchFirstObject = Nothing
    resultCount = 0
    errorText = ""

    Dim sel
    Set sel = Nothing

    On Error Resume Next
    Set sel = doc.Selection
    If Err.Number <> 0 Or sel Is Nothing Then
        errorText = Err.Description
        Err.Clear
        On Error GoTo 0
        Exit Function
    End If

    sel.Clear
    Err.Clear
    sel.Search CStr(queryText)
    If Err.Number <> 0 Then
        errorText = Err.Description
        Err.Clear
    Else
        resultCount = SelectionCount(sel)
        If resultCount > 0 Then Set SearchFirstObject = SelectionItemValue(sel, 1)
    End If
    sel.Clear
    If Err.Number <> 0 Then Err.Clear
    On Error GoTo 0
End Function

Function FindObjectByName(doc, objectName)
    Set FindObjectByName = Nothing

    Dim resultCount
    Dim errorText
    Set FindObjectByName = SearchFirstObject(doc, "Name=" & CStr(objectName) & ",all", resultCount, errorText)
    If FindObjectByName Is Nothing Then
        Set FindObjectByName = SearchFirstObject(doc, "Name=*" & CStr(objectName) & "*,all", resultCount, errorText)
    End If
End Function

Function TryUpdateNativeSymbol(symbolObj, weldID)
    Dim detailText
    TryUpdateNativeSymbol = TryUpdateNativeSymbolWithDetail(symbolObj, weldID, detailText)
End Function

Function TryUpdateNativeSymbolWithDetail(symbolObj, weldID, ByRef detailText)
    TryUpdateNativeSymbolWithDetail = False
    detailText = "no native writable field found"

    Dim props
    props = Array("PrimarySize", "PrimaryWeldSize", "Size", "Text", "TextString", "Value", "String")

    Dim i
    For i = LBound(props) To UBound(props)
        If TrySetScalarProperty(symbolObj, CStr(props(i)), weldID) Then
            detailText = "wrote " & CStr(props(i))
            TryUpdateNativeSymbolWithDetail = True
            Exit Function
        End If
    Next
End Function

Function TrySetScalarProperty(obj, propertyName, value)
    TrySetScalarProperty = False
    If obj Is Nothing Then Exit Function
    If Not IsAutomationIdentifier(propertyName) Then Exit Function

    Dim labelValue
    labelValue = CStr(value)

    On Error Resume Next
    Execute "obj." & CStr(propertyName) & " = labelValue"
    If Err.Number = 0 Then TrySetScalarProperty = True
    If Err.Number <> 0 Then Err.Clear
    On Error GoTo 0
End Function

Function TryPlaceTextNearSymbol(symbolObj, weldID)
    Dim detailText
    TryPlaceTextNearSymbol = TryPlaceTextNearSymbolWithDetail(symbolObj, weldID, detailText)
End Function

Function TryPlaceTextNearSymbolWithDetail(symbolObj, weldID, ByRef detailText)
    TryPlaceTextNearSymbolWithDetail = False
    detailText = ""

    Dim view
    Set view = ViewWithTexts(symbolObj)
    If view Is Nothing Then
        detailText = "parent DrawingView with Texts collection not accessible"
        Exit Function
    End If

    Dim x
    Dim y
    x = ProbeDouble(symbolObj, "X")
    y = ProbeDouble(symbolObj, "Y")
    If x = "" Or y = "" Then
        detailText = "symbol X/Y position not accessible"
        Exit Function
    End If

    Dim txt
    Set txt = Nothing
    On Error Resume Next
    Set txt = view.Texts.Add(CStr(weldID), CDbl(x) + 5.0, CDbl(y) + 5.0)
    If Err.Number = 0 And Not txt Is Nothing Then
        txt.Name = "LABEL_" & CStr(weldID)
        txt.SetFontSize 0, 0, 3.5
        detailText = "created LABEL_" & CStr(weldID) & " on view " & SafeObjectName(view)
        TryPlaceTextNearSymbolWithDetail = True
    Else
        detailText = "Texts.Add failed"
        If Err.Number <> 0 Then detailText = detailText & ": " & Err.Description
    End If
    If Err.Number <> 0 Then Err.Clear
    On Error GoTo 0
End Function

Function ViewWithTexts(obj)
    Set ViewWithTexts = Nothing

    Dim current
    Set current = obj

    Dim depth
    depth = 0
    Do While Not current Is Nothing And depth < 12
        Dim texts
        Set texts = Nothing
        On Error Resume Next
        Set texts = current.Texts
        If Err.Number = 0 And Not texts Is Nothing Then
            Set ViewWithTexts = current
            On Error GoTo 0
            Exit Function
        End If
        Err.Clear
        Set current = ObjectParent(current)
        On Error GoTo 0
        depth = depth + 1
    Loop
End Function

' ---------------------------------------------------------------------------
' CSV / file helpers
' ---------------------------------------------------------------------------

Function ResolveRegisterPath(doc)
    Dim fso
    Set fso = CreateObject("Scripting.FileSystemObject")

    Dim candidatePath
    Dim drawingFolder
    Dim linkedProductFolder
    Dim lastRegisterPath
    Dim inputDefault
    Dim userPath

    drawingFolder = DocumentFolderPath(doc)

    If drawingFolder <> "" Then
        candidatePath = fso.BuildPath(drawingFolder, REGISTER_FILE_NAME)

        If fso.FileExists(candidatePath) Then
            ResolveRegisterPath = candidatePath
            Exit Function
        End If
    End If

    linkedProductFolder = FindLinkedProductFolder(doc)
    If linkedProductFolder <> "" Then
        candidatePath = fso.BuildPath(linkedProductFolder, REGISTER_FILE_NAME)

        If fso.FileExists(candidatePath) Then
            Call WriteLastRegisterPath(doc, candidatePath)
            ResolveRegisterPath = candidatePath
            Exit Function
        End If

        lastRegisterPath = ReadRegisterPathFromSettingsFile(fso.BuildPath(linkedProductFolder, SETTINGS_FILE_NAME))
        If lastRegisterPath <> "" Then
            If fso.FileExists(lastRegisterPath) Then
                Call WriteLastRegisterPath(doc, lastRegisterPath)
                ResolveRegisterPath = lastRegisterPath
                Exit Function
            End If
        End If
    End If

    lastRegisterPath = ReadLastRegisterPath(doc)
    If lastRegisterPath <> "" Then
        If fso.FileExists(lastRegisterPath) Then
            ResolveRegisterPath = lastRegisterPath
            Exit Function
        End If
    End If

    inputDefault = ""
    If lastRegisterPath <> "" Then inputDefault = lastRegisterPath

    userPath = InputBox("weld_design_register.csv was not found." & vbCrLf & _
                        "Please enter the full path to weld_design_register.csv generated by BuildWeldRegisterFromWeldDesign.CATScript:", _
                        MACRO_NAME, inputDefault)

    userPath = Trim(Unquote(CStr(userPath)))
    If userPath = "" Then
        ResolveRegisterPath = ""
        Exit Function
    End If

    If Not fso.FileExists(userPath) Then
        MsgBox "Register file not found:" & vbCrLf & userPath, vbExclamation, MACRO_NAME
        ResolveRegisterPath = ""
    Else
        Call WriteLastRegisterPath(doc, userPath)
        ResolveRegisterPath = userPath
    End If
End Function

Function SettingsPath(doc)
    Dim folderPath
    folderPath = DocumentFolderPath(doc)

    If folderPath = "" Then
        folderPath = DesktopFolderPath()
    End If

    SettingsPath = CreateObject("Scripting.FileSystemObject").BuildPath(CStr(folderPath), SETTINGS_FILE_NAME)
End Function

Function ReadLastRegisterPath(doc)
    ReadLastRegisterPath = ""

    Dim fso
    Set fso = CreateObject("Scripting.FileSystemObject")

    Dim settingsFilePath
    settingsFilePath = SettingsPath(doc)
    ReadLastRegisterPath = ReadRegisterPathFromSettingsFile(settingsFilePath)
    If ReadLastRegisterPath <> "" Then Exit Function

    settingsFilePath = fso.BuildPath(DesktopFolderPath(), SETTINGS_FILE_NAME)
    ReadLastRegisterPath = ReadRegisterPathFromSettingsFile(settingsFilePath)
End Function

Function ReadRegisterPathFromSettingsFile(settingsFilePath)
    ReadRegisterPathFromSettingsFile = ""

    If Trim(CStr(settingsFilePath)) = "" Then Exit Function

    Dim fso
    Set fso = CreateObject("Scripting.FileSystemObject")
    If Not fso.FileExists(settingsFilePath) Then Exit Function

    Dim ts
    Dim lineText

    On Error Resume Next
    Set ts = fso.OpenTextFile(settingsFilePath, 1, False)
    If Err.Number <> 0 Or ts Is Nothing Then
        Err.Clear
        On Error GoTo 0
        Exit Function
    End If

    Do While Not ts.AtEndOfStream
        lineText = ts.ReadLine
        If Left(lineText, Len("LastRegisterPath=")) = "LastRegisterPath=" Then
            ReadRegisterPathFromSettingsFile = Trim(Mid(lineText, Len("LastRegisterPath=") + 1))
            Exit Do
        End If
        If Left(lineText, Len("RegisterPath=")) = "RegisterPath=" Then
            ReadRegisterPathFromSettingsFile = Trim(Mid(lineText, Len("RegisterPath=") + 1))
            Exit Do
        End If
    Loop

    ts.Close
    If Err.Number <> 0 Then Err.Clear
    On Error GoTo 0
End Function

Sub WriteLastRegisterPath(doc, registerPath)
    Dim settingsFilePath
    settingsFilePath = SettingsPath(doc)
    If settingsFilePath = "" Then Exit Sub

    On Error Resume Next
    Dim fso
    Dim ts
    Set fso = CreateObject("Scripting.FileSystemObject")
    Set ts = fso.CreateTextFile(settingsFilePath, True, False)
    If Err.Number = 0 And Not ts Is Nothing Then
        ts.WriteLine "[WeldMap]"
        ts.WriteLine "LastRegisterPath=" & CStr(registerPath)
        ts.WriteLine "RegisterPath=" & CStr(registerPath)
        ts.WriteLine "RegisterFolder=" & fso.GetParentFolderName(CStr(registerPath))
        ts.WriteLine "UpdatedAt=" & CStr(Now)
        ts.Close
    End If
    If Err.Number <> 0 Then Err.Clear
    On Error GoTo 0
End Sub

Function LoadRegisterCsv(filePath)
    Dim rows
    Set rows = NewList()
    Set LoadRegisterCsv = rows

    Dim fso
    Set fso = CreateObject("Scripting.FileSystemObject")
    If Not fso.FileExists(filePath) Then Exit Function

    Dim ts
    Set ts = fso.OpenTextFile(filePath, 1, False)
    If ts.AtEndOfStream Then
        ts.Close
        Exit Function
    End If

    Dim headers
    headers = ParseDelimitedLine(ts.ReadLine)

    Do While Not ts.AtEndOfStream
        Dim line
        line = ts.ReadLine
        If Trim(line) <> "" Then rows.Add CsvRowToDictionary(headers, ParseDelimitedLine(line))
    Loop

    ts.Close
End Function

Function ParseDelimitedLine(line)
    Dim delimiter
    If InStr(line, ";") > 0 Then
        delimiter = ";"
    ElseIf InStr(line, "|") > 0 Then
        delimiter = "|"
    Else
        delimiter = ","
    End If
    ParseDelimitedLine = Split(line, delimiter)
End Function

Function CsvRowToDictionary(headers, values)
    Dim d
    Set d = NewDictionary()

    Dim i
    For i = LBound(headers) To UBound(headers)
        If i <= UBound(values) Then
            d.Add Trim(Unquote(CStr(headers(i)))), Trim(Unquote(CStr(values(i))))
        Else
            d.Add Trim(Unquote(CStr(headers(i)))), ""
        End If
    Next
    Set CsvRowToDictionary = d
End Function

Function Unquote(value)
    Dim s
    s = CStr(value)
    If Len(s) >= 2 Then
        If Left(s, 1) = """" And Right(s, 1) = """" Then s = Mid(s, 2, Len(s) - 2)
    End If
    Unquote = Replace(s, """""", """")
End Function

Sub WriteTextFile(filePath, lines)
    Dim fso
    Set fso = CreateObject("Scripting.FileSystemObject")
    Dim ts
    Set ts = fso.CreateTextFile(filePath, True, False)
    Dim i
    For i = 0 To lines.Count - 1
        ts.WriteLine SafeText(lines.Item(i))
    Next
    ts.Close
End Sub

' ---------------------------------------------------------------------------
' Generic helpers
' ---------------------------------------------------------------------------

Function EmptyAsText(value)
    If Trim(CStr(value)) = "" Then
        EmptyAsText = "<empty>"
    Else
        EmptyAsText = CStr(value)
    End If
End Function

Function SafeObjectName(obj)
    SafeObjectName = "<not accessible>"
    If obj Is Nothing Then
        SafeObjectName = "<none>"
        Exit Function
    End If

    On Error Resume Next
    SafeObjectName = CStr(obj.Name)
    If Err.Number <> 0 Or Trim(CStr(SafeObjectName)) = "" Then
        Err.Clear
        SafeObjectName = "<unnamed>"
    End If
    On Error GoTo 0
End Function

Function SafeTypeName(obj)
    SafeTypeName = "<not accessible>"
    If obj Is Nothing Then
        SafeTypeName = "<none>"
        Exit Function
    End If

    On Error Resume Next
    SafeTypeName = TypeName(obj)
    If Err.Number <> 0 Or Trim(CStr(SafeTypeName)) = "" Then
        Err.Clear
        SafeTypeName = "<not accessible>"
    End If
    On Error GoTo 0
End Function

Function SafeScalarProperty(obj, propertyName)
    SafeScalarProperty = "<not accessible>"
    If obj Is Nothing Then Exit Function
    If Not IsAutomationIdentifier(propertyName) Then Exit Function

    Dim propertyValue
    On Error Resume Next
    propertyValue = Eval("obj." & CStr(propertyName))
    If Err.Number = 0 Then
        SafeScalarProperty = CStr(propertyValue)
        If Trim(CStr(SafeScalarProperty)) = "" Then SafeScalarProperty = "<empty>"
    Else
        Err.Clear
    End If
    On Error GoTo 0
End Function

Function SafeCollectionCount(collectionObj)
    SafeCollectionCount = 0
    If collectionObj Is Nothing Then Exit Function

    On Error Resume Next
    SafeCollectionCount = CLng(collectionObj.Count)
    If Err.Number <> 0 Then
        Err.Clear
        SafeCollectionCount = 0
    End If
    On Error GoTo 0
End Function

Function SafeChildCollectionCount(obj, collectionName)
    SafeChildCollectionCount = "<not accessible>"
    If obj Is Nothing Then Exit Function
    If Not IsAutomationIdentifier(collectionName) Then Exit Function

    Dim childCollection
    Set childCollection = Nothing

    On Error Resume Next
    Execute "Set childCollection = obj." & CStr(collectionName)
    If Err.Number = 0 And Not childCollection Is Nothing Then
        SafeChildCollectionCount = CStr(SafeCollectionCount(childCollection))
    Else
        Err.Clear
    End If
    On Error GoTo 0
End Function

Function ViewGenerativeLinkInfo(viewObj)
    ViewGenerativeLinkInfo = "<not accessible>"
    If viewObj Is Nothing Then Exit Function

    Dim behaviorObj
    Dim linkedDoc
    Set behaviorObj = Nothing
    Set linkedDoc = Nothing

    On Error Resume Next
    Set behaviorObj = viewObj.GenerativeBehavior
    If Err.Number <> 0 Or behaviorObj Is Nothing Then
        Err.Clear
        On Error GoTo 0
        Exit Function
    End If

    Set linkedDoc = behaviorObj.Document
    If Err.Number <> 0 Or linkedDoc Is Nothing Then
        Err.Clear
        Set linkedDoc = behaviorObj.ReferenceDocument
    End If

    If Err.Number = 0 And Not linkedDoc Is Nothing Then
        ViewGenerativeLinkInfo = SafeObjectName(linkedDoc) & " | " & SafeFullName(linkedDoc)
    Else
        Err.Clear
    End If
    On Error GoTo 0
End Function

Function SafeFullName(docObj)
    SafeFullName = "<not accessible>"
    If docObj Is Nothing Then
        SafeFullName = "<none>"
        Exit Function
    End If

    On Error Resume Next
    SafeFullName = CStr(docObj.FullName)
    If Err.Number <> 0 Or Trim(CStr(SafeFullName)) = "" Then
        Err.Clear
        SafeFullName = "<not accessible>"
    End If
    On Error GoTo 0
End Function

Function NewDictionary()
    Dim d
    Set d = CreateObject("Scripting.Dictionary")
    d.CompareMode = 1
    Set NewDictionary = d
End Function

Function NewList()
    Set NewList = CreateObject("System.Collections.ArrayList")
End Function

Sub ListAdd(listObj, value)
    listObj.Add SafeText(value)
End Sub

Function DictValue(d, key)
    If d Is Nothing Then
        DictValue = ""
    ElseIf d.Exists(CStr(key)) Then
        DictValue = CStr(d.Item(CStr(key)))
    Else
        DictValue = ""
    End If
End Function

Function SelectionCount(sel)
    SelectionCount = 0
    On Error Resume Next
    SelectionCount = CLng(sel.Count2)
    If Err.Number <> 0 Then
        Err.Clear
        SelectionCount = CLng(sel.Count)
    End If
    If Err.Number <> 0 Then
        Err.Clear
        SelectionCount = 0
    End If
    On Error GoTo 0
End Function

Function SelectionItemValue(sel, indexValue)
    Set SelectionItemValue = Nothing
    On Error Resume Next
    Set SelectionItemValue = sel.Item2(CLng(indexValue)).Value
    If Err.Number <> 0 Then
        Err.Clear
        Set SelectionItemValue = sel.Item(CLng(indexValue)).Value
    End If
    If Err.Number <> 0 Then
        Err.Clear
        Set SelectionItemValue = Nothing
    End If
    On Error GoTo 0
End Function

Function ObjectParent(obj)
    Set ObjectParent = Nothing
    If obj Is Nothing Then Exit Function
    On Error Resume Next
    Set ObjectParent = obj.Parent
    If Err.Number <> 0 Then
        Err.Clear
        Set ObjectParent = Nothing
    End If
    On Error GoTo 0
End Function

Function ProbeDouble(obj, propertyName)
    ProbeDouble = ""
    If obj Is Nothing Then Exit Function
    If Not IsAutomationIdentifier(propertyName) Then Exit Function
    On Error Resume Next
    Dim v
    v = Eval("obj." & CStr(propertyName))
    If Err.Number = 0 Then ProbeDouble = CStr(CDbl(v))
    If Err.Number <> 0 Then Err.Clear
    On Error GoTo 0
End Function

Function IsAutomationIdentifier(value)
    Dim s
    Dim i
    Dim ch
    s = CStr(value)
    If s = "" Then
        IsAutomationIdentifier = False
        Exit Function
    End If
    ch = Mid(s, 1, 1)
    If Not ((ch >= "A" And ch <= "Z") Or (ch >= "a" And ch <= "z") Or ch = "_") Then
        IsAutomationIdentifier = False
        Exit Function
    End If
    For i = 1 To Len(s)
        ch = Mid(s, i, 1)
        If Not ((ch >= "A" And ch <= "Z") Or (ch >= "a" And ch <= "z") Or (ch >= "0" And ch <= "9") Or ch = "_") Then
            IsAutomationIdentifier = False
            Exit Function
        End If
    Next
    IsAutomationIdentifier = True
End Function

Function CLngOrZero(value)
    On Error Resume Next
    CLngOrZero = CLng(value)
    If Err.Number <> 0 Then
        Err.Clear
        CLngOrZero = 0
    End If
    On Error GoTo 0
End Function

Function SafeText(value)
    On Error Resume Next
    Dim s
    If IsNull(value) Then
        SafeText = "<Null>"
        Exit Function
    End If
    If IsEmpty(value) Then
        SafeText = ""
        Exit Function
    End If
    s = CStr(value)
    If Err.Number <> 0 Then
        Err.Clear
        SafeText = "<CStr failed>"
        Exit Function
    End If
    s = Replace(s, Chr(0), "")
    s = Replace(s, vbCrLf, " ")
    s = Replace(s, vbCr, " ")
    s = Replace(s, vbLf, " ")
    SafeText = s
End Function

Function BuildOutputPath(doc, fileName)
    Dim folderPath
    folderPath = DocumentFolderPath(doc)

    If folderPath = "" Then
        folderPath = DesktopFolderPath()
    End If

    BuildOutputPath = CreateObject("Scripting.FileSystemObject").BuildPath(CStr(folderPath), CStr(fileName))
End Function

Function DesktopFolderPath()
    DesktopFolderPath = ""

    On Error Resume Next
    DesktopFolderPath = CreateObject("WScript.Shell").SpecialFolders("Desktop")
    If Err.Number <> 0 Or Trim(CStr(DesktopFolderPath)) = "" Then
        Err.Clear
        DesktopFolderPath = CreateObject("Scripting.FileSystemObject").GetSpecialFolder(2)
    End If
    On Error GoTo 0
End Function

Function DocumentFolderPath(doc)
    DocumentFolderPath = ""

    On Error Resume Next
    DocumentFolderPath = CStr(doc.Path)
    If Err.Number <> 0 Then
        Err.Clear
        DocumentFolderPath = ""
    End If
    On Error GoTo 0

    DocumentFolderPath = Trim(CStr(DocumentFolderPath))
End Function

Function FindLinkedProductFolder(doc)
    FindLinkedProductFolder = ""

    Dim sheets
    Set sheets = Nothing
    On Error Resume Next
    Set sheets = doc.Sheets
    If Err.Number <> 0 Or sheets Is Nothing Then
        Err.Clear
        On Error GoTo 0
        Exit Function
    End If
    On Error GoTo 0

    Dim s
    Dim v
    Dim sheet
    Dim view
    Dim folderPath

    For s = 1 To sheets.Count
        Set sheet = Nothing
        On Error Resume Next
        Set sheet = sheets.Item(s)
        If Err.Number <> 0 Or sheet Is Nothing Then
            Err.Clear
            On Error GoTo 0
        Else
            On Error GoTo 0
            For v = 1 To sheet.Views.Count
                Set view = Nothing
                On Error Resume Next
                Set view = sheet.Views.Item(v)
                If Err.Number <> 0 Or view Is Nothing Then
                    Err.Clear
                    On Error GoTo 0
                Else
                    On Error GoTo 0
                    folderPath = LinkedFolderFromView(view)
                    If folderPath <> "" Then
                        FindLinkedProductFolder = folderPath
                        Exit Function
                    End If
                End If
            Next
        End If
    Next
End Function

Function LinkedFolderFromView(view)
    LinkedFolderFromView = ""

    Dim linkedDoc
    Set linkedDoc = Nothing

    On Error Resume Next
    Set linkedDoc = view.GenerativeBehavior.Document
    If Err.Number <> 0 Or linkedDoc Is Nothing Then
        Err.Clear
        Set linkedDoc = view.GenerativeBehavior.ReferenceDocument
    End If
    If Err.Number <> 0 Then Err.Clear
    On Error GoTo 0

    If linkedDoc Is Nothing Then Exit Function

    LinkedFolderFromView = DocumentFolderPath(linkedDoc)
End Function
