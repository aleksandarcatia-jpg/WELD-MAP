Option Explicit

' ---------------------------------------------------------------------------
' ListWeldDesignObjects.CATScript
'
' Phase 1 test macro for CATIA V5 Weld Design workflow.
' It does not assign W001/W002 and does not change the model.
'
' Goal:
'   - run in an active CATProduct;
'   - find objects that look like Weld Design weld objects / Assembly Joints;
'   - list object name, type, Part A / Part B if readable, weld type/size/length
'     and exposed parameters/properties.
'
' The report is written next to the CATProduct when possible, otherwise Desktop.
' ---------------------------------------------------------------------------

Const MACRO_NAME = "ListWeldDesignObjects"
Const REPORT_FILE_NAME = "weld_design_objects_report.txt"

Sub CATMain()
    Dim doc
    Set doc = Nothing

    On Error Resume Next
    Set doc = CATIA.ActiveDocument
    On Error GoTo 0

    If doc Is Nothing Then
        MsgBox "Open CATProduct and run this macro again.", vbExclamation, MACRO_NAME
        Exit Sub
    End If

    If TypeName(doc) <> "ProductDocument" Then
        MsgBox "Active document must be CATProduct.", vbExclamation, MACRO_NAME
        Exit Sub
    End If

    Dim candidates
    Set candidates = CreateObject("Scripting.Dictionary")
    candidates.CompareMode = 1

    Call AddCandidatesFromSelectionSearch(doc, candidates)
    Call AddCandidatesFromProductTree(doc.Product, candidates)

    Dim reportLines
    Set reportLines = NewList()

    ListAdd reportLines, "CATIA Weld Design object scan"
    ListAdd reportLines, "Active document: " & SafeDocumentName(doc)
    ListAdd reportLines, "Found weld objects: " & CStr(candidates.Count)
    ListAdd reportLines, ""

    If candidates.Count = 0 Then
        ListAdd reportLines, "No Weld Design weld objects found. Use WELD_MAP fallback workflow."
    Else
        Dim key
        Dim obj
        Dim index
        index = 0

        For Each key In candidates.Keys
            index = index + 1
            Set obj = candidates.Item(key)
            Call AppendObjectReport(reportLines, obj, index)
        Next
    End If

    Dim reportPath
    reportPath = WriteReportFile(doc, reportLines)

    If candidates.Count = 0 Then
        MsgBox "No Weld Design weld objects found. Use WELD_MAP fallback workflow." & vbCrLf & _
               "Report: " & reportPath, vbExclamation, MACRO_NAME
    Else
        MsgBox "Found weld objects: " & CStr(candidates.Count) & vbCrLf & _
               "Report: " & reportPath, vbInformation, MACRO_NAME
    End If
End Sub

Sub AddCandidatesFromSelectionSearch(doc, candidates)
    Dim queries
    queries = Array( _
        "Name=*Weld*,all", _
        "Name=*WELD*,all", _
        "Name=*weld*,all", _
        "Name=*Joint*,all", _
        "Name=*JOINT*,all", _
        "Name=*Assembly*Joint*,all", _
        "Name=*Seam*,all", _
        "Name=*Welding*,all", _
        "Type=Weld,all", _
        "Type=WeldFeature,all", _
        "Type=AssemblyJoint,all", _
        "Type=Assembly Joint,all", _
        "Type=Joint,all")

    Dim i
    For i = LBound(queries) To UBound(queries)
        Call AddCandidatesFromSearchQuery(doc, candidates, CStr(queries(i)))
    Next
End Sub

Sub AddCandidatesFromSearchQuery(doc, candidates, query)
    Dim sel
    Set sel = Nothing

    On Error Resume Next
    Set sel = doc.Selection
    If sel Is Nothing Then
        On Error GoTo 0
        Exit Sub
    End If

    sel.Clear
    Err.Clear
    sel.Search CStr(query)

    If Err.Number = 0 Then
        Dim countValue
        Dim i
        Dim obj

        countValue = SelectionCount(sel)

        For i = 1 To countValue
            Set obj = SelectionItemValue(sel, i)
            If Not obj Is Nothing Then
                If IsWeldDesignCandidate(obj) Then Call AddCandidate(candidates, obj)
            End If
        Next
    End If

    Err.Clear
    sel.Clear
    On Error GoTo 0
End Sub

Sub AddCandidatesFromProductTree(product, candidates)
    If product Is Nothing Then Exit Sub

    If IsWeldDesignCandidate(product) Then Call AddCandidate(candidates, product)

    Dim children
    Set children = Nothing

    On Error Resume Next
    Set children = product.Products
    On Error GoTo 0

    If children Is Nothing Then Exit Sub

    Dim i
    Dim child

    For i = 1 To children.Count
        Set child = Nothing
        On Error Resume Next
        Set child = children.Item(i)
        On Error GoTo 0

        If Not child Is Nothing Then Call AddCandidatesFromProductTree(child, candidates)
    Next
End Sub

Function IsWeldDesignCandidate(obj)
    Dim textValue
    textValue = UCase(ObjectName(obj) & " " & ObjectTypeName(obj))

    IsWeldDesignCandidate = False

    If InStr(textValue, "WELD") > 0 Then IsWeldDesignCandidate = True
    If InStr(textValue, "WELDING") > 0 Then IsWeldDesignCandidate = True
    If InStr(textValue, "JOINT") > 0 Then IsWeldDesignCandidate = True
    If InStr(textValue, "ASSEMBLYJOINT") > 0 Then IsWeldDesignCandidate = True
    If InStr(textValue, "SEAM") > 0 Then IsWeldDesignCandidate = True
End Function

Sub AddCandidate(candidates, obj)
    Dim key
    key = CandidateKey(obj)

    If key = "" Then Exit Sub

    If Not candidates.Exists(key) Then candidates.Add key, obj
End Sub

Function CandidateKey(obj)
    CandidateKey = UCase(ObjectTypeName(obj) & "|" & ObjectName(obj) & "|" & ParentPath(obj, 4))
End Function

Sub AppendObjectReport(reportLines, obj, index)
    ListAdd reportLines, "------------------------------------------------------------"
    ListAdd reportLines, "Object #" & CStr(index)
    ListAdd reportLines, "Object name: " & ObjectName(obj)
    ListAdd reportLines, "Object type: " & ObjectTypeName(obj)
    ListAdd reportLines, "Parent path: " & ParentPath(obj, 8)
    ListAdd reportLines, "Part A: " & CandidatePartA(obj)
    ListAdd reportLines, "Part B: " & CandidatePartB(obj)
    ListAdd reportLines, "Weld type: " & CandidateValue(obj, Array("WeldType", "Weld Type", "Type"))
    ListAdd reportLines, "Weld size: " & CandidateValue(obj, Array("WeldSize", "Weld Size", "Size", "Throat"))
    ListAdd reportLines, "Weld length: " & CandidateValue(obj, Array("WeldLength", "Weld Length", "Length"))
    ListAdd reportLines, "Available parameters/properties:"
    Call AppendParameterReport(reportLines, obj, 80)
    ListAdd reportLines, ""
End Sub

Function CandidatePartA(obj)
    CandidatePartA = FirstNonEmpty(Array( _
        ObjectDescriptionFromObjectProperty(obj, "PartA"), _
        ObjectDescriptionFromObjectProperty(obj, "ConnectedPartA"), _
        ObjectDescriptionFromObjectProperty(obj, "FirstPart"), _
        ObjectDescriptionFromObjectProperty(obj, "Reference1"), _
        ObjectDescriptionFromObjectProperty(obj, "Support1"), _
        ObjectDescriptionFromObjectProperty(obj, "Element1")))
End Function

Function CandidatePartB(obj)
    CandidatePartB = FirstNonEmpty(Array( _
        ObjectDescriptionFromObjectProperty(obj, "PartB"), _
        ObjectDescriptionFromObjectProperty(obj, "ConnectedPartB"), _
        ObjectDescriptionFromObjectProperty(obj, "SecondPart"), _
        ObjectDescriptionFromObjectProperty(obj, "Reference2"), _
        ObjectDescriptionFromObjectProperty(obj, "Support2"), _
        ObjectDescriptionFromObjectProperty(obj, "Element2")))
End Function

Function ObjectDescriptionFromObjectProperty(obj, propertyName)
    ObjectDescriptionFromObjectProperty = ""

    ' VBScript has no CallByName, so the likely Weld Design property names are tried explicitly.
    Select Case UCase(CStr(propertyName))
        Case "PARTA"
            ObjectDescriptionFromObjectProperty = DescribePartAProperty(obj)
        Case "CONNECTEDPARTA"
            ObjectDescriptionFromObjectProperty = DescribeConnectedPartAProperty(obj)
        Case "FIRSTPART"
            ObjectDescriptionFromObjectProperty = DescribeFirstPartProperty(obj)
        Case "REFERENCE1"
            ObjectDescriptionFromObjectProperty = DescribeReference1Property(obj)
        Case "SUPPORT1"
            ObjectDescriptionFromObjectProperty = DescribeSupport1Property(obj)
        Case "ELEMENT1"
            ObjectDescriptionFromObjectProperty = DescribeElement1Property(obj)
        Case "PARTB"
            ObjectDescriptionFromObjectProperty = DescribePartBProperty(obj)
        Case "CONNECTEDPARTB"
            ObjectDescriptionFromObjectProperty = DescribeConnectedPartBProperty(obj)
        Case "SECONDPART"
            ObjectDescriptionFromObjectProperty = DescribeSecondPartProperty(obj)
        Case "REFERENCE2"
            ObjectDescriptionFromObjectProperty = DescribeReference2Property(obj)
        Case "SUPPORT2"
            ObjectDescriptionFromObjectProperty = DescribeSupport2Property(obj)
        Case "ELEMENT2"
            ObjectDescriptionFromObjectProperty = DescribeElement2Property(obj)
    End Select
End Function

Function DescribePartAProperty(obj)
    On Error Resume Next
    Dim refObj
    Set refObj = obj.PartA
    If Err.Number = 0 And Not refObj Is Nothing Then DescribePartAProperty = DescribeModelObject(refObj)
    Err.Clear
    On Error GoTo 0
End Function

Function DescribeConnectedPartAProperty(obj)
    On Error Resume Next
    Dim refObj
    Set refObj = obj.ConnectedPartA
    If Err.Number = 0 And Not refObj Is Nothing Then DescribeConnectedPartAProperty = DescribeModelObject(refObj)
    Err.Clear
    On Error GoTo 0
End Function

Function DescribeFirstPartProperty(obj)
    On Error Resume Next
    Dim refObj
    Set refObj = obj.FirstPart
    If Err.Number = 0 And Not refObj Is Nothing Then DescribeFirstPartProperty = DescribeModelObject(refObj)
    Err.Clear
    On Error GoTo 0
End Function

Function DescribeReference1Property(obj)
    On Error Resume Next
    Dim refObj
    Set refObj = obj.Reference1
    If Err.Number = 0 And Not refObj Is Nothing Then DescribeReference1Property = DescribeModelObject(refObj)
    Err.Clear
    On Error GoTo 0
End Function

Function DescribeSupport1Property(obj)
    On Error Resume Next
    Dim refObj
    Set refObj = obj.Support1
    If Err.Number = 0 And Not refObj Is Nothing Then DescribeSupport1Property = DescribeModelObject(refObj)
    Err.Clear
    On Error GoTo 0
End Function

Function DescribeElement1Property(obj)
    On Error Resume Next
    Dim refObj
    Set refObj = obj.Element1
    If Err.Number = 0 And Not refObj Is Nothing Then DescribeElement1Property = DescribeModelObject(refObj)
    Err.Clear
    On Error GoTo 0
End Function

Function DescribePartBProperty(obj)
    On Error Resume Next
    Dim refObj
    Set refObj = obj.PartB
    If Err.Number = 0 And Not refObj Is Nothing Then DescribePartBProperty = DescribeModelObject(refObj)
    Err.Clear
    On Error GoTo 0
End Function

Function DescribeConnectedPartBProperty(obj)
    On Error Resume Next
    Dim refObj
    Set refObj = obj.ConnectedPartB
    If Err.Number = 0 And Not refObj Is Nothing Then DescribeConnectedPartBProperty = DescribeModelObject(refObj)
    Err.Clear
    On Error GoTo 0
End Function

Function DescribeSecondPartProperty(obj)
    On Error Resume Next
    Dim refObj
    Set refObj = obj.SecondPart
    If Err.Number = 0 And Not refObj Is Nothing Then DescribeSecondPartProperty = DescribeModelObject(refObj)
    Err.Clear
    On Error GoTo 0
End Function

Function DescribeReference2Property(obj)
    On Error Resume Next
    Dim refObj
    Set refObj = obj.Reference2
    If Err.Number = 0 And Not refObj Is Nothing Then DescribeReference2Property = DescribeModelObject(refObj)
    Err.Clear
    On Error GoTo 0
End Function

Function DescribeSupport2Property(obj)
    On Error Resume Next
    Dim refObj
    Set refObj = obj.Support2
    If Err.Number = 0 And Not refObj Is Nothing Then DescribeSupport2Property = DescribeModelObject(refObj)
    Err.Clear
    On Error GoTo 0
End Function

Function DescribeElement2Property(obj)
    On Error Resume Next
    Dim refObj
    Set refObj = obj.Element2
    If Err.Number = 0 And Not refObj Is Nothing Then DescribeElement2Property = DescribeModelObject(refObj)
    Err.Clear
    On Error GoTo 0
End Function

Function DescribeModelObject(obj)
    Dim nameValue
    Dim typeValue
    Dim partNumber

    nameValue = ObjectName(obj)
    typeValue = ObjectTypeName(obj)
    partNumber = ""

    On Error Resume Next
    partNumber = CStr(obj.PartNumber)
    If Err.Number <> 0 Then
        Err.Clear
        partNumber = CStr(obj.ReferenceProduct.PartNumber)
    End If
    If Err.Number <> 0 Then
        Err.Clear
        partNumber = ""
    End If
    On Error GoTo 0

    If partNumber <> "" Then
        DescribeModelObject = partNumber & " (" & typeValue & ": " & nameValue & ")"
    Else
        DescribeModelObject = typeValue & ": " & nameValue
    End If
End Function

Function CandidateValue(obj, names)
    Dim value
    value = ParameterValueByNames(obj, names)

    If value = "" Then value = DirectWeldPropertyValue(obj, names)

    CandidateValue = value
End Function

Function DirectWeldPropertyValue(obj, names)
    DirectWeldPropertyValue = ""

    Dim i
    Dim n

    For i = LBound(names) To UBound(names)
        n = NormalizeName(names(i))

        If n = "WELDTYPE" Or n = "TYPE" Then
            DirectWeldPropertyValue = DirectTypeValue(obj)
        ElseIf n = "WELDSIZE" Or n = "SIZE" Or n = "THROAT" Then
            DirectWeldPropertyValue = DirectSizeValue(obj)
        ElseIf n = "WELDLENGTH" Or n = "LENGTH" Then
            DirectWeldPropertyValue = DirectLengthValue(obj)
        End If

        If DirectWeldPropertyValue <> "" Then Exit Function
    Next
End Function

Function DirectTypeValue(obj)
    On Error Resume Next
    DirectTypeValue = CStr(obj.WeldType)
    If Err.Number <> 0 Then
        Err.Clear
        DirectTypeValue = CStr(obj.Type)
    End If
    If Err.Number <> 0 Then
        Err.Clear
        DirectTypeValue = ""
    End If
    On Error GoTo 0
End Function

Function DirectSizeValue(obj)
    On Error Resume Next
    DirectSizeValue = CStr(obj.WeldSize)
    If Err.Number <> 0 Then
        Err.Clear
        DirectSizeValue = CStr(obj.Size)
    End If
    If Err.Number <> 0 Then
        Err.Clear
        DirectSizeValue = ""
    End If
    On Error GoTo 0
End Function

Function DirectLengthValue(obj)
    On Error Resume Next
    DirectLengthValue = CStr(obj.WeldLength)
    If Err.Number <> 0 Then
        Err.Clear
        DirectLengthValue = CStr(obj.Length.Value)
    End If
    If Err.Number <> 0 Then
        Err.Clear
        DirectLengthValue = CStr(obj.Length)
    End If
    If Err.Number <> 0 Then
        Err.Clear
        DirectLengthValue = ""
    End If
    On Error GoTo 0
End Function

Function ParameterValueByNames(obj, names)
    ParameterValueByNames = ""

    Dim params
    Set params = ObjectParameters(obj)
    If params Is Nothing Then Exit Function

    Dim i
    Dim p
    Dim value

    For i = LBound(names) To UBound(names)
        Set p = Nothing
        On Error Resume Next
        Set p = params.Item(CStr(names(i)))
        If Err.Number = 0 And Not p Is Nothing Then
            value = ParameterToString(p)
            If value <> "" Then
                ParameterValueByNames = value
                On Error GoTo 0
                Exit Function
            End If
        End If
        Err.Clear
        On Error GoTo 0
    Next

    Dim j
    Dim normalizedParam
    Dim normalizedName

    For j = 1 To ParameterCount(params)
        Set p = ParameterItem(params, j)
        If Not p Is Nothing Then
            normalizedParam = NormalizeName(ObjectName(p))

            For i = LBound(names) To UBound(names)
                normalizedName = NormalizeName(names(i))
                If normalizedName <> "" Then
                    If InStr(normalizedParam, normalizedName) > 0 Then
                        value = ParameterToString(p)
                        If value <> "" Then
                            ParameterValueByNames = value
                            Exit Function
                        End If
                    End If
                End If
            Next
        End If
    Next
End Function

Sub AppendParameterReport(reportLines, obj, maxCount)
    Dim wroteAny
    wroteAny = False

    Dim params
    Set params = ObjectParameters(obj)

    If Not params Is Nothing Then
        Dim countValue
        Dim i
        Dim p
        countValue = ParameterCount(params)

        If countValue > 0 Then
            For i = 1 To countValue
                If i > CLng(maxCount) Then
                    ListAdd reportLines, "  ... parameter list truncated at " & CStr(maxCount)
                    Exit For
                End If

                Set p = ParameterItem(params, i)
                If Not p Is Nothing Then
                    ListAdd reportLines, "  PARAM " & CStr(i) & ": " & ObjectName(p) & " = " & ParameterToString(p)
                    wroteAny = True
                End If
            Next
        End If
    End If

    Call AppendUserPropertiesReport(reportLines, obj, maxCount, wroteAny)

    If Not wroteAny Then ListAdd reportLines, "  (No exposed parameters/properties read by this test macro.)"
End Sub

Sub AppendUserPropertiesReport(reportLines, obj, maxCount, ByRef wroteAny)
    Dim props
    Set props = Nothing

    On Error Resume Next
    Set props = obj.UserRefProperties
    If props Is Nothing Then Set props = obj.UserProperties
    On Error GoTo 0

    If props Is Nothing Then Exit Sub

    Dim countValue
    Dim i
    Dim p

    countValue = CollectionCount(props)

    For i = 1 To countValue
        If i > CLng(maxCount) Then
            ListAdd reportLines, "  ... property list truncated at " & CStr(maxCount)
            Exit For
        End If

        Set p = CollectionItem(props, i)
        If Not p Is Nothing Then
            ListAdd reportLines, "  PROP " & CStr(i) & ": " & ObjectName(p) & " = " & ParameterToString(p)
            wroteAny = True
        End If
    Next
End Sub

Function ObjectParameters(obj)
    Set ObjectParameters = Nothing

    On Error Resume Next
    Set ObjectParameters = obj.Parameters
    If ObjectParameters Is Nothing Then Set ObjectParameters = obj.Parent.Parameters
    If ObjectParameters Is Nothing Then Set ObjectParameters = obj.ReferenceProduct.Parameters
    On Error GoTo 0
End Function

Function ParameterCount(params)
    ParameterCount = CollectionCount(params)
End Function

Function ParameterItem(params, indexValue)
    Set ParameterItem = CollectionItem(params, indexValue)
End Function

Function CollectionCount(collection)
    CollectionCount = 0
    If collection Is Nothing Then Exit Function

    On Error Resume Next
    Err.Clear
    CollectionCount = CLng(collection.Count)
    If Err.Number <> 0 Then
        Err.Clear
        CollectionCount = CLng(collection.Count2)
    End If
    If Err.Number <> 0 Then
        Err.Clear
        CollectionCount = 0
    End If
    On Error GoTo 0
End Function

Function CollectionItem(collection, indexValue)
    Set CollectionItem = Nothing
    If collection Is Nothing Then Exit Function

    On Error Resume Next
    Set CollectionItem = collection.Item(CLng(indexValue))
    If CollectionItem Is Nothing Then Set CollectionItem = collection.Item2(CLng(indexValue))
    On Error GoTo 0
End Function

Function SelectionCount(sel)
    SelectionCount = 0
    If sel Is Nothing Then Exit Function

    On Error Resume Next
    Err.Clear
    SelectionCount = CLng(sel.Count2)
    If Err.Number <> 0 Then
        Err.Clear
        SelectionCount = CLng(sel.Count)
    End If
    If Err.Number <> 0 Then
        Err.Clear
        SelectionCount = 0
    End If
    On Error GoTo 0
End Function

Function SelectionItemValue(sel, indexValue)
    Set SelectionItemValue = Nothing
    If sel Is Nothing Then Exit Function

    Dim item
    Set item = Nothing

    On Error Resume Next
    Set item = sel.Item2(CLng(indexValue))
    If item Is Nothing Then Set item = sel.Item(CLng(indexValue))
    If Not item Is Nothing Then Set SelectionItemValue = item.Value
    On Error GoTo 0
End Function

Function ObjectName(obj)
    ObjectName = ""
    If obj Is Nothing Then Exit Function

    On Error Resume Next
    ObjectName = CStr(obj.Name)
    If Err.Number <> 0 Then
        Err.Clear
        ObjectName = CStr(obj.PartNumber)
    End If
    If Err.Number <> 0 Then
        Err.Clear
        ObjectName = ""
    End If
    On Error GoTo 0
End Function

Function ObjectTypeName(obj)
    ObjectTypeName = ""
    If obj Is Nothing Then Exit Function

    On Error Resume Next
    ObjectTypeName = TypeName(obj)
    If Err.Number <> 0 Then
        Err.Clear
        ObjectTypeName = ""
    End If
    On Error GoTo 0
End Function

Function ParentPath(obj, maxDepth)
    ParentPath = ""

    Dim current
    Set current = obj

    Dim i
    Dim part

    For i = 1 To CLng(maxDepth)
        If current Is Nothing Then Exit For

        part = ObjectTypeName(current) & ":" & ObjectName(current)
        If ParentPath = "" Then
            ParentPath = part
        Else
            ParentPath = part & " > " & ParentPath
        End If

        On Error Resume Next
        Set current = current.Parent
        If Err.Number <> 0 Then
            Err.Clear
            Set current = Nothing
        End If
        On Error GoTo 0
    Next
End Function

Function ParameterToString(parameter)
    ParameterToString = ""
    If parameter Is Nothing Then Exit Function

    On Error Resume Next
    ParameterToString = CStr(parameter.ValueAsString)
    If Err.Number <> 0 Then
        Err.Clear
        ParameterToString = CStr(parameter.Value)
    End If
    If Err.Number <> 0 Then
        Err.Clear
        ParameterToString = CStr(parameter)
    End If
    If Err.Number <> 0 Then
        Err.Clear
        ParameterToString = ""
    End If
    On Error GoTo 0
End Function

Function FirstNonEmpty(values)
    Dim i
    FirstNonEmpty = ""

    For i = LBound(values) To UBound(values)
        If Trim(CStr(values(i))) <> "" Then
            FirstNonEmpty = CStr(values(i))
            Exit Function
        End If
    Next
End Function

Function NormalizeName(value)
    Dim s
    s = UCase(CStr(value))
    s = Replace(s, " ", "")
    s = Replace(s, "_", "")
    s = Replace(s, "-", "")
    s = Replace(s, ".", "")
    s = Replace(s, "/", "")
    NormalizeName = s
End Function

Function NewList()
    Dim list
    Set list = CreateObject("Scripting.Dictionary")
    Set NewList = list
End Function

Sub ListAdd(list, value)
    list.Add CStr(list.Count), CStr(value)
End Sub

Function SafeDocumentName(doc)
    SafeDocumentName = ""
    On Error Resume Next
    SafeDocumentName = CStr(doc.FullName)
    If Err.Number <> 0 Or SafeDocumentName = "" Then
        Err.Clear
        SafeDocumentName = CStr(doc.Name)
    End If
    If Err.Number <> 0 Then
        Err.Clear
        SafeDocumentName = ""
    End If
    On Error GoTo 0
End Function

Function WriteReportFile(doc, reportLines)
    WriteReportFile = ""

    Dim folderPath
    folderPath = ReportFolder(doc)

    Dim fso
    Set fso = CreateObject("Scripting.FileSystemObject")

    If Not fso.FolderExists(folderPath) Then folderPath = DesktopFolder()

    Dim filePath
    filePath = fso.BuildPath(folderPath, REPORT_FILE_NAME)

    Dim ts
    On Error Resume Next
    Set ts = fso.CreateTextFile(filePath, True)
    If Err.Number <> 0 Or ts Is Nothing Then
        Err.Clear
        filePath = fso.BuildPath(DesktopFolder(), REPORT_FILE_NAME)
        Set ts = fso.CreateTextFile(filePath, True)
    End If

    If Not ts Is Nothing Then
        Dim i
        For i = 0 To reportLines.Count - 1
            ts.WriteLine CStr(reportLines.Item(CStr(i)))
        Next
        ts.Close
        WriteReportFile = filePath
    End If
    On Error GoTo 0
End Function

Function ReportFolder(doc)
    ReportFolder = ""

    Dim fullName
    fullName = ""

    On Error Resume Next
    fullName = CStr(doc.FullName)
    On Error GoTo 0

    If fullName <> "" Then
        Dim fso
        Set fso = CreateObject("Scripting.FileSystemObject")
        ReportFolder = fso.GetParentFolderName(fullName)
    End If

    If ReportFolder = "" Then ReportFolder = DesktopFolder()
End Function

Function DesktopFolder()
    DesktopFolder = ""

    On Error Resume Next
    DesktopFolder = CreateObject("WScript.Shell").SpecialFolders("Desktop")
    If Err.Number <> 0 Or DesktopFolder = "" Then
        Err.Clear
        DesktopFolder = CreateObject("Scripting.FileSystemObject").GetSpecialFolder(2)
    End If
    On Error GoTo 0
End Function
