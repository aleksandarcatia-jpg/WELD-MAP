Option Explicit

' ==========================================================
' CATIA V5 - Weld Map Assistant MVP
' Author: MS Trace / CATIA WeldMap Concept
'
' Function:
' 1. Select Part A geometry
' 2. Select Part B geometry
' 3. Select existing weld geometry inside WELD_MAP.CATPart
' 4. Create Weld ID
' 5. Rename selected weld geometry as WELD_W001
' 6. Store weld attributes as CATIA parameters
' 7. Export Weld Register CSV
'
' IMPORTANT:
' Works with an active CATPart or an active CATProduct containing WELD_MAP.CATPart.
' Weld geometry must already exist in any user-created Geometrical Set inside WELD_MAP.CATPart.
' ==========================================================

Sub CATMain()

    Dim doc
    Set doc = CATIA.ActiveDocument

    If doc Is Nothing Then
        MsgBox "No active CATIA document."
        Exit Sub
    End If

    Dim part

    If TypeName(doc) = "PartDocument" Then

        Set part = doc.Part

    ElseIf TypeName(doc) = "ProductDocument" Then

        Set part = GetActiveWeldMapPartFromProduct(doc)

        If part Is Nothing Then
            MsgBox "WELD_MAP CATPart nije pronadjen u sklopu." & vbCrLf & _
                   "Proveri da u product tree postoji part koji u nazivu ima WELD_MAP, Weld map, WELDMAP ili WELD MAP."
            Exit Sub
        End If

    Else

        MsgBox "Aktivni dokument mora biti CATPart ili CATProduct."
        Exit Sub

    End If

    Dim sel
    Set sel = doc.Selection

    Dim partAElement
    Set partAElement = SelectAnyObject(sel, "Select geometry from Part A")

    If partAElement Is Nothing Then
        MsgBox "Part A selection cancelled."
        Exit Sub
    End If

    Dim partBElement
    Set partBElement = SelectAnyObject(sel, "Select geometry from Part B")

    If partBElement Is Nothing Then
        MsgBox "Part B selection cancelled."
        Exit Sub
    End If

    Dim weldElement
    Set weldElement = SelectAnyObject(sel, "Select existing weld geometry inside WELD_MAP.CATPart")

    If weldElement Is Nothing Then
        MsgBox "Weld geometry selection cancelled."
        Exit Sub
    End If

    Dim weldID
    weldID = GetNextWeldID(part)

    Dim partA_Number, partA_Instance, partA_Name, partA_PositionNo
    Dim partA_Material, partA_Thickness, partA_Dimension

    Dim partB_Number, partB_Instance, partB_Name, partB_PositionNo
    Dim partB_Material, partB_Thickness, partB_Dimension

    partA_Number = GetSelectionInfo(partAElement, "NUMBER", part)
    partA_Instance = GetSelectionInfo(partAElement, "INSTANCE", part)
    partA_Name = GetSelectionInfo(partAElement, "NAME", part)
    partA_PositionNo = GetSelectionInfo(partAElement, "POSITION", part)
    partA_Material = GetSelectionInfo(partAElement, "MATERIAL", part)
    partA_Thickness = GetSelectionInfo(partAElement, "THICKNESS", part)
    partA_Dimension = GetSelectionInfo(partAElement, "DIMENSION", part)

    partB_Number = GetSelectionInfo(partBElement, "NUMBER", part)
    partB_Instance = GetSelectionInfo(partBElement, "INSTANCE", part)
    partB_Name = GetSelectionInfo(partBElement, "NAME", part)
    partB_PositionNo = GetSelectionInfo(partBElement, "POSITION", part)
    partB_Material = GetSelectionInfo(partBElement, "MATERIAL", part)
    partB_Thickness = GetSelectionInfo(partBElement, "THICKNESS", part)
    partB_Dimension = GetSelectionInfo(partBElement, "DIMENSION", part)

    Dim weldGeometry
    Set weldGeometry = GetExistingWeldGeometryInWeldMap(part, weldElement)

    If weldGeometry Is Nothing Then
        MsgBox "Selected weld geometry is not inside WELD_MAP.CATPart." & vbCrLf & _
               "Please create/select the weld line, circle or helix inside WELD_MAP.CATPart."
        Exit Sub
    End If

    part.Update

    Dim weldLength
    weldLength = GetGeometryLength(part.Parent, part, weldGeometry)

    Dim weldType, weldSize, grooveDepth, grooveAngle, rootGapMm
    Dim wpsNo, weldingProcess, fillerType, fillerTradeName, fillerDesignation, fillerDiameter
    Dim shieldingGas, correctionFactor, calculatedAreaMm2, calculatedFillerConsumptionRateKgM
    Dim finalFillerConsumptionRateKgM, estimatedFillerConsumptionKg
    Dim weldLengthM, gasBottleType, gasBottleRatioKgPerBottle, estimatedGasBottles200Bar
    Dim gasBottleVolumeL, gasBottlePressureBar, gasPerBottleL, gasPerKgFillerL
    Dim estimatedGasLiters, estimatedGasBottles40L200bar
    Dim vtReq, ptReq, utReq, remark, estimateWarning

    If Not CollectWeldData(weldLength, weldLengthM, weldType, weldSize, grooveDepth, grooveAngle, rootGapMm, _
                           wpsNo, weldingProcess, fillerType, fillerTradeName, fillerDesignation, fillerDiameter, shieldingGas, _
                           correctionFactor, calculatedAreaMm2, calculatedFillerConsumptionRateKgM, _
                           finalFillerConsumptionRateKgM, estimatedFillerConsumptionKg, gasBottleType, _
                           gasBottleRatioKgPerBottle, estimatedGasBottles200Bar, gasBottleVolumeL, _
                           gasBottlePressureBar, gasPerBottleL, gasPerKgFillerL, estimatedGasLiters, _
                           estimatedGasBottles40L200bar, vtReq, ptReq, utReq, remark, estimateWarning) Then
        Exit Sub
    End If

    If estimateWarning <> "" Then
        MsgBox estimateWarning, vbExclamation, "Estimated consumption"
    End If

    On Error Resume Next
    weldGeometry.Name = "WELD_" & weldID

    If Err.Number <> 0 Then
        Err.Clear
        On Error GoTo 0
        MsgBox "Selected weld geometry could not be renamed to WELD_" & weldID & "."
        Exit Sub
    End If

    On Error GoTo 0
    part.Update

    Dim anchorX, anchorY, anchorZ, anchorCreated
    anchorCreated = CreateWeldAnchorPoint(part.Parent, part, weldGeometry, weldID, anchorX, anchorY, anchorZ)

    Call SaveWeldParameter(part, weldID, "WeldID", weldID)
    If anchorCreated Then
        Call SaveWeldParameter(part, weldID, "LabelPointX", anchorX)
        Call SaveWeldParameter(part, weldID, "LabelPointY", anchorY)
        Call SaveWeldParameter(part, weldID, "LabelPointZ", anchorZ)
        Call SaveWeldParameter(part, weldID, "AnchorName", "ANCHOR_" & weldID)
        Call SaveWeldParameter(part, weldID, "PreferredView", "Auto")
    End If

    Call SaveWeldParameter(part, weldID, "PartA_Number", partA_Number)
    Call SaveWeldParameter(part, weldID, "PartA_Instance", partA_Instance)
    Call SaveWeldParameter(part, weldID, "PartA_PositionNo", partA_PositionNo)
    Call SaveWeldParameter(part, weldID, "PartA_Name", partA_Name)
    Call SaveWeldParameter(part, weldID, "PartA_Material", partA_Material)
    Call SaveWeldParameter(part, weldID, "PartA_Thickness", partA_Thickness)
    Call SaveWeldParameter(part, weldID, "PartA_Dimension", partA_Dimension)

    Call SaveWeldParameter(part, weldID, "PartB_Number", partB_Number)
    Call SaveWeldParameter(part, weldID, "PartB_Instance", partB_Instance)
    Call SaveWeldParameter(part, weldID, "PartB_PositionNo", partB_PositionNo)
    Call SaveWeldParameter(part, weldID, "PartB_Name", partB_Name)
    Call SaveWeldParameter(part, weldID, "PartB_Material", partB_Material)
    Call SaveWeldParameter(part, weldID, "PartB_Thickness", partB_Thickness)
    Call SaveWeldParameter(part, weldID, "PartB_Dimension", partB_Dimension)

    Call SaveWeldParameter(part, weldID, "WeldType", weldType)
    Call SaveWeldParameter(part, weldID, "WeldSize", weldSize)
    Call SaveWeldParameter(part, weldID, "GrooveDepth", grooveDepth)
    Call SaveWeldParameter(part, weldID, "GrooveAngle", grooveAngle)
    Call SaveWeldParameter(part, weldID, "RootGap_mm", rootGapMm)
    Call SaveWeldParameter(part, weldID, "RootGap", rootGapMm)
    Call SaveWeldParameter(part, weldID, "WeldLength", weldLength)
    Call SaveWeldParameter(part, weldID, "WeldLength_mm", weldLength)
    Call SaveWeldParameter(part, weldID, "WeldLength_m", weldLengthM)
    Call SaveWeldParameter(part, weldID, "WPS", wpsNo)
    Call SaveWeldParameter(part, weldID, "WeldingProcess", weldingProcess)
    Call SaveWeldParameter(part, weldID, "FillerType", fillerType)
    Call SaveWeldParameter(part, weldID, "FillerTradeName", fillerTradeName)
    Call SaveWeldParameter(part, weldID, "FillerDesignation", fillerDesignation)
    Call SaveWeldParameter(part, weldID, "FillerDiameter", fillerDiameter)
    Call SaveWeldParameter(part, weldID, "ShieldingGas", shieldingGas)
    Call SaveWeldParameter(part, weldID, "CorrectionFactor", correctionFactor)
    Call SaveWeldParameter(part, weldID, "CalculatedArea_mm2", calculatedAreaMm2)
    Call SaveWeldParameter(part, weldID, "CalculatedFillerConsumptionRate_kg_m", calculatedFillerConsumptionRateKgM)
    Call SaveWeldParameter(part, weldID, "FinalFillerConsumptionRate_kg_m", finalFillerConsumptionRateKgM)
    Call SaveWeldParameter(part, weldID, "FillerConsumptionRate_kg_m", finalFillerConsumptionRateKgM)
    Call SaveWeldParameter(part, weldID, "FillerConsumption_kg", estimatedFillerConsumptionKg)
    Call SaveWeldParameter(part, weldID, "EstimatedFillerConsumption_kg", estimatedFillerConsumptionKg)
    Call SaveWeldParameter(part, weldID, "GasBottleType", gasBottleType)
    Call SaveWeldParameter(part, weldID, "GasBottleRatio_kg_per_bottle", gasBottleRatioKgPerBottle)
    Call SaveWeldParameter(part, weldID, "EstimatedGasBottles_200bar", estimatedGasBottles200Bar)
    Call SaveWeldParameter(part, weldID, "GasBottleVolume_L", gasBottleVolumeL)
    Call SaveWeldParameter(part, weldID, "GasBottlePressure_bar", gasBottlePressureBar)
    Call SaveWeldParameter(part, weldID, "GasPerBottle_L", gasPerBottleL)
    Call SaveWeldParameter(part, weldID, "GasPerKgFiller_L", gasPerKgFillerL)
    Call SaveWeldParameter(part, weldID, "EstimatedGasLiters", estimatedGasLiters)
    Call SaveWeldParameter(part, weldID, "EstimatedGasBottles_40L_200bar", estimatedGasBottles40L200bar)
    Call SaveWeldParameter(part, weldID, "VT", vtReq)
    Call SaveWeldParameter(part, weldID, "PT", ptReq)
    Call SaveWeldParameter(part, weldID, "UT", utReq)
    Call SaveWeldParameter(part, weldID, "Remark", remark)

    part.Update

    MsgBox "Weld created:" & vbCrLf & _
           "Weld ID: " & weldID & vbCrLf & _
           "WPS: " & wpsNo & vbCrLf & _
           "Process: " & weldingProcess & vbCrLf & _
           "Size: " & weldSize & vbCrLf & _
           "Length mm: " & weldLength & vbCrLf & _
           "Length m: " & weldLengthM & vbCrLf & _
           "Final kg/m: " & finalFillerConsumptionRateKgM & vbCrLf & _
           "Estimated filler kg: " & estimatedFillerConsumptionKg & vbCrLf & _
           "Estimated gas liters: " & estimatedGasLiters & " L" & vbCrLf & _
           "Estimated gas bottles 40L/200bar: " & estimatedGasBottles40L200bar

    Dim exportNow
    exportNow = MsgBox("Export Weld Register CSV now?", vbYesNo, "Export")

    If exportNow = vbYes Then
        Call ExportWeldRegisterCSV(part)
    End If

End Sub


' ==========================================================
' SELECTION
' ==========================================================

Function SelectAnyObject(selection, message)

    Dim filter(0)
    filter(0) = "AnyObject"

    selection.Clear

    Dim status
    status = selection.SelectElement2(filter, message, False)

    If status <> "Normal" Then
        Set SelectAnyObject = Nothing
        Exit Function
    End If

    Set SelectAnyObject = selection.Item2(1)

End Function


' ==========================================================
' WELD DATA INPUT FLOW
' ==========================================================

Function CollectWeldData(weldLengthMmText, ByRef weldLengthM, ByRef weldType, ByRef weldSize, ByRef grooveDepth, ByRef grooveAngle, _
                         ByRef rootGapMm, ByRef wpsNo, ByRef weldingProcess, ByRef fillerType, _
                         ByRef fillerTradeName, ByRef fillerDesignation, ByRef fillerDiameter, ByRef shieldingGas, _
                         ByRef correctionFactor, ByRef calculatedAreaMm2, ByRef calculatedFillerConsumptionRateKgM, _
                         ByRef finalFillerConsumptionRateKgM, ByRef estimatedFillerConsumptionKg, _
                         ByRef gasBottleType, ByRef gasBottleRatioKgPerBottle, ByRef estimatedGasBottles200Bar, _
                         ByRef gasBottleVolumeL, ByRef gasBottlePressureBar, ByRef gasPerBottleL, _
                         ByRef gasPerKgFillerL, ByRef estimatedGasLiters, ByRef estimatedGasBottles40L200bar, _
                         ByRef vtReq, ByRef ptReq, ByRef utReq, ByRef remark, ByRef estimateWarning)

    CollectWeldData = False

    Dim weldLengthMm
    weldLengthMm = ParseDecimalValue(weldLengthMmText)

    If CStr(weldLengthMm) = "" Then
        MsgBox "Weld length could not be measured. Filler and gas estimates cannot be calculated."
        Exit Function
    End If

    weldLengthM = FormatEstimatedNumber(CDbl(weldLengthMm) / 1000, 4)

    weldType = UCase(Trim(InputBox("Enter weld type: FW / BW", "Weld Type", "FW")))
    If weldType = "" Then Exit Function

    If weldType <> "FW" And weldType <> "BW" Then
        MsgBox "WeldType must be FW or BW."
        Exit Function
    End If

    weldSize = ""
    grooveDepth = ""
    grooveAngle = ""
    rootGapMm = ""
    shieldingGas = ""
    correctionFactor = "1.20"
    calculatedAreaMm2 = ""
    calculatedFillerConsumptionRateKgM = ""
    finalFillerConsumptionRateKgM = ""
    estimatedFillerConsumptionKg = ""
    gasBottleType = "40 L / 200 bar"
    gasBottleRatioKgPerBottle = "20"
    estimatedGasBottles200Bar = ""
    gasBottleVolumeL = "40"
    gasBottlePressureBar = "200"
    gasPerBottleL = "8000"
    gasPerKgFillerL = "400"
    estimatedGasLiters = ""
    estimatedGasBottles40L200bar = ""
    estimateWarning = ""

    If weldType = "FW" Then

        weldSize = InputBox("Enter WeldSize: a3, a4, a5, a6 or manual input", "Weld Size", "a5")
        If weldSize = "" Then Exit Function

    ElseIf weldType = "BW" Then

        weldSize = InputBox("Enter WeldSize for BW, optional. Use '-' if not applicable.", "Weld Size", "-")
        If weldSize = "" Then weldSize = "-"

        grooveDepth = InputBox("Enter GrooveDepth: S5 / S8 / S10 or manual input", "Groove Depth", "S8")
        If grooveDepth = "" Then Exit Function

        grooveAngle = InputBox("Enter GrooveAngle: 30 / 45 / 60 or manual input", "Groove Angle", "45")
        If grooveAngle = "" Then Exit Function

        rootGapMm = InputBox("RootGap_mm, optional. Empty = 2 mm", "Root Gap", "2")
        If rootGapMm = "" Then rootGapMm = "2"
        If CStr(ParseDecimalValue(rootGapMm)) = "" Then rootGapMm = "2"
        rootGapMm = FormatEstimatedNumber(ParseDecimalValue(rootGapMm), 3)

    End If

    correctionFactor = InputBox("CorrectionFactor for estimated filler consumption", "Correction Factor", "1.20")
    If correctionFactor = "" Then correctionFactor = "1.20"
    If CStr(ParseDecimalValue(correctionFactor)) = "" Then correctionFactor = "1.20"
    correctionFactor = FormatEstimatedNumber(ParseDecimalValue(correctionFactor), 3)

    wpsNo = InputBox("Enter WPS number", "WPS", "WPS-")
    If wpsNo = "" Then Exit Function

    weldingProcess = Trim(InputBox("Enter WeldingProcess: 111 / 131 / 135 / 136 / 141", "Welding Process", "135"))
    If Not IsSupportedWeldingProcess(weldingProcess) Then
        MsgBox "WeldingProcess must be one of: 111, 131, 135, 136, 141."
        Exit Function
    End If

    Select Case weldingProcess

        Case "131", "135"
            fillerType = "Wire"
            fillerTradeName = InputBox("FillerTradeName", "Filler Trade Name", "")
            fillerDesignation = InputBox("FillerDesignation / WireDesignation", "Filler Designation", "")
            fillerDiameter = InputBox("FillerDiameter: 0.8 / 1.0 / 1.2 or manual input", "Filler Diameter", "1.2")
            shieldingGas = InputBox("ShieldingGas, optional", "Shielding Gas", "M21")

        Case "136"
            fillerType = "Flux-cored wire"
            fillerTradeName = InputBox("FillerTradeName", "Filler Trade Name", "")
            fillerDesignation = InputBox("FillerDesignation / Flux-cored wire designation", "Filler Designation", "")
            fillerDiameter = InputBox("FillerDiameter: 0.8 / 1.0 / 1.2 or manual input", "Filler Diameter", "1.2")
            shieldingGas = InputBox("ShieldingGas, optional", "Shielding Gas", "M21")

        Case "141"
            fillerType = "Rod"
            fillerTradeName = InputBox("FillerTradeName", "Filler Trade Name", "")
            fillerDesignation = InputBox("FillerDesignation / RodDesignation", "Filler Designation", "")
            fillerDiameter = InputBox("FillerDiameter: 1.2 / 1.6 / 2.0 / 2.4 or manual input", "Filler Diameter", "2.4")
            shieldingGas = InputBox("ShieldingGas, optional", "Shielding Gas", "I1")

        Case "111"
            fillerType = "Electrode"
            fillerTradeName = InputBox("FillerTradeName / ElectrodeTradeName", "Filler Trade Name", "")
            fillerDesignation = InputBox("ElectrodeDesignation", "Electrode Designation", "")
            fillerDiameter = InputBox("FillerDiameter: 2.4 / 3.2 / 4.0 or manual input", "Filler Diameter", "3.2")
            shieldingGas = ""

    End Select

    Call CalculateWeldConsumptionEstimates(weldLengthMm, weldType, weldSize, grooveDepth, grooveAngle, rootGapMm, _
                                           correctionFactor, weldingProcess, calculatedAreaMm2, _
                                           calculatedFillerConsumptionRateKgM, finalFillerConsumptionRateKgM, _
                                           estimatedFillerConsumptionKg, gasBottleType, gasBottleRatioKgPerBottle, _
                                           estimatedGasBottles200Bar, gasBottleVolumeL, gasBottlePressureBar, _
                                           gasPerBottleL, gasPerKgFillerL, estimatedGasLiters, _
                                           estimatedGasBottles40L200bar, estimateWarning)

    If finalFillerConsumptionRateKgM = "" Then
        Exit Function
    End If

    vtReq = InputBox("VT requirement %", "VT", "100")
    ptReq = InputBox("PT requirement %", "PT", "20")
    utReq = InputBox("UT requirement %", "UT", "0")
    remark = InputBox("Remark", "Remark", "-")

    CollectWeldData = True

End Function


Function IsSupportedWeldingProcess(weldingProcess)

    Select Case Trim(CStr(weldingProcess))
        Case "111", "131", "135", "136", "141"
            IsSupportedWeldingProcess = True
        Case Else
            IsSupportedWeldingProcess = False
    End Select

End Function


Sub CalculateWeldConsumptionEstimates(weldLengthMm, weldType, weldSize, grooveDepth, grooveAngle, rootGapMm, _
                                      correctionFactor, weldingProcess, ByRef calculatedAreaMm2, _
                                      ByRef calculatedFillerConsumptionRateKgM, ByRef finalFillerConsumptionRateKgM, _
                                      ByRef estimatedFillerConsumptionKg, ByRef gasBottleType, _
                                      ByRef gasBottleRatioKgPerBottle, ByRef estimatedGasBottles200Bar, _
                                      ByRef gasBottleVolumeL, ByRef gasBottlePressureBar, ByRef gasPerBottleL, _
                                      ByRef gasPerKgFillerL, ByRef estimatedGasLiters, _
                                      ByRef estimatedGasBottles40L200bar, _
                                      ByRef estimateWarning)

    calculatedAreaMm2 = ""
    calculatedFillerConsumptionRateKgM = ""
    finalFillerConsumptionRateKgM = ""
    estimatedFillerConsumptionKg = ""
    gasBottleType = "40 L / 200 bar"
    gasBottleRatioKgPerBottle = "20"
    estimatedGasBottles200Bar = ""
    gasBottleVolumeL = "40"
    gasBottlePressureBar = "200"
    gasPerBottleL = "8000"
    gasPerKgFillerL = "400"
    estimatedGasLiters = ""
    estimatedGasBottles40L200bar = ""
    estimateWarning = ""

    Dim cf
    cf = ParseDecimalValue(correctionFactor)

    If CStr(cf) = "" Then
        cf = 1.2
    End If

    Dim area
    area = CalculateWeldAreaMm2(weldType, weldSize, grooveDepth, grooveAngle, rootGapMm)

    If CStr(area) <> "" Then
        calculatedAreaMm2 = FormatEstimatedNumber(area, 3)
        calculatedFillerConsumptionRateKgM = FormatEstimatedNumber(CDbl(area) * 0.00785 * CDbl(cf), 4)
    Else
        estimateWarning = "Calculated filler consumption rate could not be calculated from weld geometry inputs."
    End If

    If calculatedFillerConsumptionRateKgM <> "" Then
        Dim acceptRate
        acceptRate = MsgBox("Calculated filler consumption rate: " & calculatedFillerConsumptionRateKgM & " kg/m" & vbCrLf & _
                            "Accept calculated kg/m?", vbYesNo, "Estimated filler consumption")

        If acceptRate = vbYes Then
            finalFillerConsumptionRateKgM = calculatedFillerConsumptionRateKgM
        Else
            finalFillerConsumptionRateKgM = InputBox("Manual FinalFillerConsumptionRate_kg_m", "Manual Filler Consumption Rate", calculatedFillerConsumptionRateKgM)
        End If
    Else
        finalFillerConsumptionRateKgM = InputBox("Manual FinalFillerConsumptionRate_kg_m", "Manual Filler Consumption Rate", "")
    End If

    If finalFillerConsumptionRateKgM = "" Then Exit Sub

    Dim finalRate
    finalRate = ParseDecimalValue(finalFillerConsumptionRateKgM)

    If CStr(finalRate) = "" Then
        MsgBox "FinalFillerConsumptionRate_kg_m must be numeric."
        finalFillerConsumptionRateKgM = ""
        Exit Sub
    End If

    finalFillerConsumptionRateKgM = FormatEstimatedNumber(finalRate, 4)
    estimatedFillerConsumptionKg = FormatEstimatedNumber((CDbl(weldLengthMm) / 1000) * CDbl(finalRate), 4)

    If Trim(CStr(weldingProcess)) = "111" Then
        estimatedGasLiters = "0"
        estimatedGasBottles40L200bar = "0"
        estimatedGasBottles200Bar = "0"
    ElseIf IsGasShieldedWeldingProcess(weldingProcess) Then
        estimatedGasLiters = FormatEstimatedNumber(CDbl(estimatedFillerConsumptionKg) * CDbl(gasPerKgFillerL), 4)
        estimatedGasBottles40L200bar = FormatEstimatedNumber(CDbl(estimatedGasLiters) / CDbl(gasPerBottleL), 4)
        estimatedGasBottles200Bar = estimatedGasBottles40L200bar
    Else
        estimatedGasLiters = "0"
        estimatedGasBottles40L200bar = "0"
        estimatedGasBottles200Bar = "0"
    End If

End Sub


Function IsGasShieldedWeldingProcess(weldingProcess)

    Select Case Trim(CStr(weldingProcess))
        Case "131", "135", "136", "141"
            IsGasShieldedWeldingProcess = True
        Case Else
            IsGasShieldedWeldingProcess = False
    End Select

End Function


Function CalculateWeldAreaMm2(weldType, weldSize, grooveDepth, grooveAngle, rootGapMm)

    CalculateWeldAreaMm2 = ""

    If UCase(CStr(weldType)) = "FW" Then

        Dim a
        a = ExtractNumericValueFromText(weldSize)

        If CStr(a) = "" Then Exit Function

        CalculateWeldAreaMm2 = CDbl(a) * CDbl(a)

    ElseIf UCase(CStr(weldType)) = "BW" Then

        Dim s
        s = ExtractNumericValueFromText(grooveDepth)

        Dim angle
        angle = ExtractNumericValueFromText(grooveAngle)

        Dim rootGap
        rootGap = ParseDecimalValue(rootGapMm)

        If CStr(rootGap) = "" Then
            rootGap = 2
        End If

        If CStr(s) = "" Or CStr(angle) = "" Then Exit Function

        CalculateWeldAreaMm2 = (CDbl(s) * CDbl(s) * Tan((CDbl(angle) / 2) * GetPi() / 180)) + (CDbl(rootGap) * CDbl(s))

    End If

End Function


Function ExtractNumericValueFromText(value)

    On Error Resume Next

    ExtractNumericValueFromText = ""

    Dim re
    Set re = CreateObject("VBScript.RegExp")

    re.Pattern = "([0-9]+([.,][0-9]+)?)"
    re.IgnoreCase = True
    re.Global = False

    If re.Test(CStr(value)) Then
        Dim matches
        Set matches = re.Execute(CStr(value))
        ExtractNumericValueFromText = ParseDecimalValue(matches.Item(0).SubMatches.Item(0))
    End If

    If Err.Number <> 0 Then
        Err.Clear
        ExtractNumericValueFromText = ""
    End If

    On Error GoTo 0

End Function


Function GetPi()

    GetPi = 4 * Atn(1)

End Function


Function ParseDecimalValue(value)

    On Error Resume Next

    Dim s
    s = Trim(CStr(value))
    s = Replace(s, " ", "")
    s = Replace(s, ",", ".")

    If s = "" Then
        ParseDecimalValue = ""
        Exit Function
    End If

    Dim sign
    sign = 1

    If Left(s, 1) = "-" Then
        sign = -1
        s = Mid(s, 2)
    End If

    Dim parts
    parts = Split(s, ".")

    If UBound(parts) > 1 Then
        ParseDecimalValue = ""
        Exit Function
    End If

    If parts(0) = "" Or Not IsDigits(parts(0)) Then
        ParseDecimalValue = ""
        Exit Function
    End If

    Dim result
    result = CDbl(CLng(parts(0)))

    If UBound(parts) = 1 Then
        If parts(1) = "" Or Not IsDigits(parts(1)) Then
            ParseDecimalValue = ""
            Exit Function
        End If

        result = result + (CDbl(CLng(parts(1))) / (10 ^ Len(parts(1))))
    End If

    ParseDecimalValue = CDbl(sign) * CDbl(result)

    If Err.Number <> 0 Then
        Err.Clear
        ParseDecimalValue = ""
    End If

    On Error GoTo 0

End Function


Function IsDigits(value)

    Dim s
    s = CStr(value)

    If s = "" Then
        IsDigits = False
        Exit Function
    End If

    Dim i
    Dim ch

    For i = 1 To Len(s)
        ch = Mid(s, i, 1)
        If ch < "0" Or ch > "9" Then
            IsDigits = False
            Exit Function
        End If
    Next

    IsDigits = True

End Function


Function FormatEstimatedNumber(value, decimals)

    On Error Resume Next

    FormatEstimatedNumber = CStr(Round(CDbl(value), CInt(decimals)))

    If Err.Number <> 0 Then
        Err.Clear
        FormatEstimatedNumber = ""
    End If

    On Error GoTo 0

End Function


' ==========================================================
' EXISTING WELD GEOMETRY ASSIGNMENT
' ==========================================================

Function GetExistingWeldGeometryInWeldMap(weldMapPart, weldElement)

    On Error Resume Next

    Set GetExistingWeldGeometryInWeldMap = Nothing

    Dim selectedWeldGeometry
    Set selectedWeldGeometry = weldElement.Value

    If selectedWeldGeometry Is Nothing Then
        On Error GoTo 0
        Exit Function
    End If

    If Not IsSelectedGeometryInsideWeldMapPart(weldMapPart, weldElement, selectedWeldGeometry) Then
        On Error GoTo 0
        Exit Function
    End If

    Set GetExistingWeldGeometryInWeldMap = selectedWeldGeometry

    On Error GoTo 0

End Function


Function AssignExistingWeldGeometryInWeldMap(weldMapPart, weldElement, weldID)

    On Error Resume Next

    Set AssignExistingWeldGeometryInWeldMap = Nothing

    Dim selectedWeldGeometry
    Set selectedWeldGeometry = GetExistingWeldGeometryInWeldMap(weldMapPart, weldElement)

    If selectedWeldGeometry Is Nothing Then
        On Error GoTo 0
        Exit Function
    End If

    selectedWeldGeometry.Name = "WELD_" & weldID
    weldMapPart.Update

    If Err.Number <> 0 Then
        Err.Clear
        Set AssignExistingWeldGeometryInWeldMap = Nothing
    Else
        Set AssignExistingWeldGeometryInWeldMap = selectedWeldGeometry
    End If

    On Error GoTo 0

End Function


Function IsSelectedGeometryInsideWeldMapPart(weldMapPart, weldElement, selectedGeometry)

    On Error Resume Next

    IsSelectedGeometryInsideWeldMapPart = False

    If IsObjectInPartHybridBodies(weldMapPart, selectedGeometry) Then
        IsSelectedGeometryInsideWeldMapPart = True
        On Error GoTo 0
        Exit Function
    End If

    Dim leafProduct
    Set leafProduct = Nothing
    Set leafProduct = weldElement.LeafProduct

    If Err.Number <> 0 Then
        Err.Clear
        Set leafProduct = Nothing
    End If

    If Not leafProduct Is Nothing Then

        Dim refProduct
        Set refProduct = leafProduct.ReferenceProduct

        Dim parentDoc
        Set parentDoc = refProduct.Parent

        If TypeName(parentDoc) = "PartDocument" Then
            If parentDoc.Part Is weldMapPart Then
                IsSelectedGeometryInsideWeldMapPart = True
                On Error GoTo 0
                Exit Function
            End If
        End If

    End If

    Dim ref
    Set ref = Nothing
    Set ref = weldMapPart.CreateReferenceFromObject(selectedGeometry)

    If Err.Number = 0 Then
        If Not ref Is Nothing Then
            IsSelectedGeometryInsideWeldMapPart = True
        End If
    Else
        Err.Clear
    End If

    On Error GoTo 0

End Function


Function IsObjectInPartHybridBodies(part, targetObj)

    On Error Resume Next

    IsObjectInPartHybridBodies = False

    Dim i
    Dim hb

    For i = 1 To part.HybridBodies.Count

        Set hb = part.HybridBodies.Item(i)

        If IsObjectInHybridBodyRecursive(hb, targetObj) Then
            IsObjectInPartHybridBodies = True
            On Error GoTo 0
            Exit Function
        End If

    Next

    On Error GoTo 0

End Function


Function IsObjectInHybridBodyRecursive(hb, targetObj)

    On Error Resume Next

    IsObjectInHybridBodyRecursive = False

    Dim i
    Dim hs

    For i = 1 To hb.HybridShapes.Count

        Set hs = hb.HybridShapes.Item(i)

        If hs Is targetObj Then
            IsObjectInHybridBodyRecursive = True
            On Error GoTo 0
            Exit Function
        End If

    Next

    Dim subHb
    For i = 1 To hb.HybridBodies.Count

        Set subHb = hb.HybridBodies.Item(i)

        If IsObjectInHybridBodyRecursive(subHb, targetObj) Then
            IsObjectInHybridBodyRecursive = True
            On Error GoTo 0
            Exit Function
        End If

    Next

    On Error GoTo 0

End Function


' ==========================================================
' WELD ID
' ==========================================================

Function GetNextWeldID(part)

    Dim maxNo
    maxNo = 0

    ' 1) Search existing weld parameters
    On Error Resume Next

    Dim params
    Set params = part.Parameters

    Dim i
    For i = 1 To params.Count

        Dim pName
        pName = CStr(params.Item(i).Name)

        Dim n1
        n1 = 0

        If Left(UCase(pName), 6) = "WELD_W" Then
            n1 = ExtractWeldNumberFromText(pName)
        End If

        If n1 > maxNo Then
            maxNo = n1
        End If

    Next

    On Error GoTo 0

    ' 2) Search existing weld geometries inside all Geometrical Sets
    On Error Resume Next

    Dim hb
    For i = 1 To part.HybridBodies.Count

        Set hb = part.HybridBodies.Item(i)

        Dim n2
        n2 = GetMaxWeldNumberInHybridBody(hb)

        If n2 > maxNo Then
            maxNo = n2
        End If

    Next

    On Error GoTo 0

    maxNo = maxNo + 1

    If maxNo < 10 Then
        GetNextWeldID = "W00" & CStr(maxNo)
    ElseIf maxNo < 100 Then
        GetNextWeldID = "W0" & CStr(maxNo)
    Else
        GetNextWeldID = "W" & CStr(maxNo)
    End If

End Function


Function ExtractWeldNumberFromText(value)

    On Error Resume Next

    Dim re
    Set re = CreateObject("VBScript.RegExp")

    ' Matches W001, WELD_W001, WELD_W001_WPS, etc.
    re.Pattern = "W([0-9]{1,5})"
    re.IgnoreCase = True
    re.Global = False

    If re.Test(CStr(value)) Then
        Dim matches
        Set matches = re.Execute(CStr(value))

        ExtractWeldNumberFromText = CInt(matches.Item(0).SubMatches.Item(0))
    Else
        ExtractWeldNumberFromText = 0
    End If

    If Err.Number <> 0 Then
        Err.Clear
        ExtractWeldNumberFromText = 0
    End If

    On Error GoTo 0

End Function


Function GetMaxWeldNumberInHybridBody(hb)

    On Error Resume Next

    Dim maxNo
    maxNo = 0

    Dim i
    Dim hs

    For i = 1 To hb.HybridShapes.Count

        Set hs = hb.HybridShapes.Item(i)

        Dim n
        n = ExtractWeldNumberFromText(CStr(hs.Name))

        If n > maxNo Then
            maxNo = n
        End If

    Next

    Dim subHb
    For i = 1 To hb.HybridBodies.Count

        Set subHb = hb.HybridBodies.Item(i)

        Dim childMax
        childMax = GetMaxWeldNumberInHybridBody(subHb)

        If childMax > maxNo Then
            maxNo = childMax
        End If

    Next

    GetMaxWeldNumberInHybridBody = maxNo

    On Error GoTo 0

End Function


' ==========================================================
' SAVE / READ PARAMETERS
' ==========================================================

Sub SaveWeldParameter(part, weldID, fieldName, fieldValue)

    Dim paramName
    paramName = "WELD_" & weldID & "_" & fieldName

    Call SetStringParameter(part, paramName, CStr(fieldValue))

End Sub


Sub SetStringParameter(part, paramName, paramValue)

    Dim params
    Set params = part.Parameters

    Dim p

    On Error Resume Next
    Set p = params.Item(paramName)

    If Err.Number <> 0 Then
        Err.Clear
        Set p = params.CreateString(paramName, paramValue)
    Else
        p.Value = paramValue
    End If

    On Error GoTo 0

End Sub


Function GetStringParameter(part, paramName)

    Dim params
    Set params = part.Parameters

    Dim p
    On Error Resume Next
    Set p = params.Item(paramName)

    If Err.Number <> 0 Then
        Err.Clear
        GetStringParameter = ""
    Else
        GetStringParameter = CStr(p.ValueAsString)
        If GetStringParameter = "" Then
            GetStringParameter = CStr(p.Value)
        End If
    End If

    On Error GoTo 0

End Function


' ==========================================================
' SELECTION INFO
' ==========================================================

Function GetSelectionInfo(selElement, infoType, activePart)

    On Error Resume Next

    Dim result
    result = ""

    Dim obj
    Set obj = selElement.Value

    Dim leafProduct
    Set leafProduct = selElement.LeafProduct

    If Err.Number = 0 Then

        If Not leafProduct Is Nothing Then

            Select Case UCase(infoType)

                Case "NUMBER"
                    result = CStr(leafProduct.PartNumber)

                Case "INSTANCE"
                    result = CStr(leafProduct.Name)

                Case "NAME"
                    result = CStr(leafProduct.Nomenclature)
                    If result = "" Then result = CStr(leafProduct.Name)

                Case "POSITION"
                    result = GetProductProperty(leafProduct, "MS_PositionNo")
                    If result = "" Then result = GetProductProperty(leafProduct, "PositionNo")
                    If result = "" Then result = CStr(leafProduct.Name)

                Case "MATERIAL"
                    result = GetProductProperty(leafProduct, "MS_Material")
                    If result = "" Then result = GetProductProperty(leafProduct, "Material")

                Case "THICKNESS"
                    result = GetProductProperty(leafProduct, "MS_Thickness")
                    If result = "" Then result = GetProductProperty(leafProduct, "Thickness")

                Case "DIMENSION"
                    result = GetProductProperty(leafProduct, "MS_Dimension")
                    If result = "" Then result = GetProductProperty(leafProduct, "Dimension")

            End Select

        End If

    End If

    Err.Clear

    If result = "" Then

        Select Case UCase(infoType)

            Case "NUMBER"
                result = GetPartParameter(activePart, "MS_PartNumber")
                If result = "" Then result = activePart.Name

            Case "INSTANCE"
                result = obj.Name

            Case "NAME"
                result = GetPartParameter(activePart, "MS_PartName")
                If result = "" Then result = obj.Name

            Case "POSITION"
                result = GetPartParameter(activePart, "MS_PositionNo")

            Case "MATERIAL"
                result = GetPartParameter(activePart, "MS_Material")
                If result = "" Then result = GetPartParameter(activePart, "Material")

            Case "THICKNESS"
                result = GetPartParameter(activePart, "MS_Thickness")
                If result = "" Then result = GetPartParameter(activePart, "Thickness")

            Case "DIMENSION"
                result = GetPartParameter(activePart, "MS_Dimension")
                If result = "" Then result = GetPartParameter(activePart, "Dimension")

        End Select

    End If

    On Error GoTo 0

    GetSelectionInfo = result

End Function


Function GetProductProperty(product, propName)

    On Error Resume Next

    Dim props
    Set props = product.UserRefProperties

    Dim p
    Set p = props.Item(propName)

    If Err.Number <> 0 Then
        Err.Clear
        GetProductProperty = ""
    Else
        GetProductProperty = CStr(p.ValueAsString)
        If GetProductProperty = "" Then
            GetProductProperty = CStr(p.Value)
        End If
    End If

    On Error GoTo 0

End Function


Function GetPartParameter(part, paramName)

    On Error Resume Next

    Dim p
    Set p = part.Parameters.Item(paramName)

    If Err.Number <> 0 Then
        Err.Clear
        GetPartParameter = ""
    Else
        GetPartParameter = CStr(p.ValueAsString)
        If GetPartParameter = "" Then
            GetPartParameter = CStr(p.Value)
        End If
    End If

    On Error GoTo 0

End Function


' ==========================================================
' LENGTH MEASUREMENT
' ==========================================================

Function GetGeometryLength(doc, part, obj)

    On Error Resume Next

    Dim ref
    Set ref = part.CreateReferenceFromObject(obj)

    Dim spa
    Set spa = doc.GetWorkbench("SPAWorkbench")

    Dim measurable
    Set measurable = spa.GetMeasurable(ref)

    Dim l
    l = measurable.Length

    If Err.Number <> 0 Then
        Err.Clear
        GetGeometryLength = ""
    Else
        GetGeometryLength = CStr(Round(l, 3))
    End If

    On Error GoTo 0

End Function


' ==========================================================
' WELD ANCHOR POINTS
' ==========================================================

Function CreateWeldAnchorPoint(doc, part, weldGeometry, weldID, ByRef x, ByRef y, ByRef z)

    CreateWeldAnchorPoint = False

    If Not CalculateGeometryAnchorPoint(doc, part, weldGeometry, x, y, z) Then
        Exit Function
    End If

    Call DeleteNamedObjectInPart(part.Parent, "ANCHOR_" & weldID)

    Dim hb
    Set hb = GetOrCreateHybridBody(part, "WELD_ANCHORS")

    If hb Is Nothing Then
        Exit Function
    End If

    Dim hsf
    Dim point
    Set hsf = Nothing
    Set point = Nothing

    On Error Resume Next
    Set hsf = part.HybridShapeFactory
    Set point = hsf.AddNewPointCoord(CDbl(x), CDbl(y), CDbl(z))

    If Err.Number <> 0 Or point Is Nothing Then
        Err.Clear
        On Error GoTo 0
        Exit Function
    End If

    point.Name = "ANCHOR_" & weldID
    hb.AppendHybridShape point
    part.Update

    If Err.Number = 0 Then
        CreateWeldAnchorPoint = True
    Else
        Err.Clear
    End If

    On Error GoTo 0

End Function


Function CalculateGeometryAnchorPoint(doc, part, obj, ByRef x, ByRef y, ByRef z)

    CalculateGeometryAnchorPoint = False

    On Error Resume Next

    Dim ref
    Set ref = part.CreateReferenceFromObject(obj)

    Dim spa
    Set spa = doc.GetWorkbench("SPAWorkbench")

    Dim measurable
    Set measurable = spa.GetMeasurable(ref)

    If Err.Number <> 0 Or measurable Is Nothing Then
        Err.Clear
        On Error GoTo 0
        Exit Function
    End If

    Dim pts(8)
    Dim coords(2)
    Dim box(5)

    Err.Clear
    measurable.GetPointsOnCurve pts
    If Err.Number = 0 Then
        x = FormatEstimatedNumber(CDbl(pts(3)), 4)
        y = FormatEstimatedNumber(CDbl(pts(4)), 4)
        z = FormatEstimatedNumber(CDbl(pts(5)), 4)
        CalculateGeometryAnchorPoint = True
        On Error GoTo 0
        Exit Function
    End If

    Err.Clear
    measurable.GetCenter coords
    If Err.Number = 0 Then
        x = FormatEstimatedNumber(CDbl(coords(0)), 4)
        y = FormatEstimatedNumber(CDbl(coords(1)), 4)
        z = FormatEstimatedNumber(CDbl(coords(2)), 4)
        CalculateGeometryAnchorPoint = True
        On Error GoTo 0
        Exit Function
    End If

    Err.Clear
    measurable.GetCOG coords
    If Err.Number = 0 Then
        x = FormatEstimatedNumber(CDbl(coords(0)), 4)
        y = FormatEstimatedNumber(CDbl(coords(1)), 4)
        z = FormatEstimatedNumber(CDbl(coords(2)), 4)
        CalculateGeometryAnchorPoint = True
        On Error GoTo 0
        Exit Function
    End If

    Err.Clear
    measurable.GetBoundingBox box
    If Err.Number = 0 Then
        x = FormatEstimatedNumber((CDbl(box(0)) + CDbl(box(3))) / 2, 4)
        y = FormatEstimatedNumber((CDbl(box(1)) + CDbl(box(4))) / 2, 4)
        z = FormatEstimatedNumber((CDbl(box(2)) + CDbl(box(5))) / 2, 4)
        CalculateGeometryAnchorPoint = True
    Else
        Err.Clear
    End If

    On Error GoTo 0

End Function


Function GetOrCreateHybridBody(part, hybridBodyName)

    Set GetOrCreateHybridBody = Nothing

    Dim hbs
    Dim hb
    Dim i

    On Error Resume Next
    Set hbs = part.HybridBodies

    For i = 1 To hbs.Count
        Set hb = hbs.Item(i)
        If UCase(CStr(hb.Name)) = UCase(CStr(hybridBodyName)) Then
            Set GetOrCreateHybridBody = hb
            On Error GoTo 0
            Exit Function
        End If
    Next

    Set hb = hbs.Add()
    hb.Name = CStr(hybridBodyName)
    Set GetOrCreateHybridBody = hb

    If Err.Number <> 0 Then
        Err.Clear
        Set GetOrCreateHybridBody = Nothing
    End If

    On Error GoTo 0

End Function


Sub DeleteNamedObjectInPart(partDoc, objectName)

    On Error Resume Next

    Dim sel
    Set sel = partDoc.Selection
    sel.Clear
    sel.Search "Name=" & CStr(objectName) & ",all"

    If sel.Count2 > 0 Then
        sel.Delete
    End If

    sel.Clear
    Err.Clear
    On Error GoTo 0

End Sub


' ==========================================================
' EXPORT CSV
' ==========================================================

Sub ExportWeldRegisterCSV(part)

    Dim defaultPath
    defaultPath = "C:\Temp\catia_weld_register.csv"

    Dim outputPath
    outputPath = InputBox("Enter CSV export path:", "Export Weld Register", defaultPath)

    If outputPath = "" Then
        Exit Sub
    End If

    Dim fso
    Set fso = CreateObject("Scripting.FileSystemObject")

    Dim folderPath
    folderPath = fso.GetParentFolderName(outputPath)

    If folderPath <> "" Then
        Call EnsureFolderExists(fso, folderPath)
    End If

    Dim file
    Set file = fso.CreateTextFile(outputPath, True)

    file.WriteLine "WeldID,PartA_Number,PartA_Instance,PartA_PositionNo,PartA_Name,PartA_Material,PartA_Thickness,PartA_Dimension,PartB_Number,PartB_Instance,PartB_PositionNo,PartB_Name,PartB_Material,PartB_Thickness,PartB_Dimension,WeldType,WeldSize,GrooveDepth,GrooveAngle,RootGap_mm,WeldLength_mm,WeldLength_m,WPS,WeldingProcess,FillerType,FillerTradeName,FillerDesignation,FillerDiameter,CorrectionFactor,CalculatedArea_mm2,CalculatedFillerConsumptionRate_kg_m,FinalFillerConsumptionRate_kg_m,EstimatedFillerConsumption_kg,GasBottleVolume_L,GasBottlePressure_bar,GasPerBottle_L,GasPerKgFiller_L,EstimatedGasLiters,EstimatedGasBottles_40L_200bar,VT,PT,UT,Remark"

    Dim weldIDs
    Set weldIDs = GetAllWeldIDs(part)

    Dim key
    For Each key In weldIDs.Keys

        Dim row
        row = Csv(GetStringParameter(part, "WELD_" & key & "_WeldID")) & "," & _
              Csv(GetStringParameter(part, "WELD_" & key & "_PartA_Number")) & "," & _
              Csv(GetStringParameter(part, "WELD_" & key & "_PartA_Instance")) & "," & _
              Csv(GetStringParameter(part, "WELD_" & key & "_PartA_PositionNo")) & "," & _
              Csv(GetStringParameter(part, "WELD_" & key & "_PartA_Name")) & "," & _
              Csv(GetStringParameter(part, "WELD_" & key & "_PartA_Material")) & "," & _
              Csv(GetStringParameter(part, "WELD_" & key & "_PartA_Thickness")) & "," & _
              Csv(GetStringParameter(part, "WELD_" & key & "_PartA_Dimension")) & "," & _
              Csv(GetStringParameter(part, "WELD_" & key & "_PartB_Number")) & "," & _
              Csv(GetStringParameter(part, "WELD_" & key & "_PartB_Instance")) & "," & _
              Csv(GetStringParameter(part, "WELD_" & key & "_PartB_PositionNo")) & "," & _
              Csv(GetStringParameter(part, "WELD_" & key & "_PartB_Name")) & "," & _
              Csv(GetStringParameter(part, "WELD_" & key & "_PartB_Material")) & "," & _
              Csv(GetStringParameter(part, "WELD_" & key & "_PartB_Thickness")) & "," & _
              Csv(GetStringParameter(part, "WELD_" & key & "_PartB_Dimension")) & "," & _
              Csv(GetStringParameter(part, "WELD_" & key & "_WeldType")) & "," & _
              Csv(GetStringParameter(part, "WELD_" & key & "_WeldSize")) & "," & _
              Csv(GetStringParameter(part, "WELD_" & key & "_GrooveDepth")) & "," & _
              Csv(GetStringParameter(part, "WELD_" & key & "_GrooveAngle")) & "," & _
              Csv(GetStringParameter(part, "WELD_" & key & "_RootGap_mm")) & "," & _
              Csv(GetStringParameter(part, "WELD_" & key & "_WeldLength_mm")) & "," & _
              Csv(GetStringParameter(part, "WELD_" & key & "_WeldLength_m")) & "," & _
              Csv(GetStringParameter(part, "WELD_" & key & "_WPS")) & "," & _
              Csv(GetStringParameter(part, "WELD_" & key & "_WeldingProcess")) & "," & _
              Csv(GetStringParameter(part, "WELD_" & key & "_FillerType")) & "," & _
              Csv(GetStringParameter(part, "WELD_" & key & "_FillerTradeName")) & "," & _
              Csv(GetStringParameter(part, "WELD_" & key & "_FillerDesignation")) & "," & _
              Csv(GetStringParameter(part, "WELD_" & key & "_FillerDiameter")) & "," & _
              Csv(GetStringParameter(part, "WELD_" & key & "_CorrectionFactor")) & "," & _
              Csv(GetStringParameter(part, "WELD_" & key & "_CalculatedArea_mm2")) & "," & _
              Csv(GetStringParameter(part, "WELD_" & key & "_CalculatedFillerConsumptionRate_kg_m")) & "," & _
              Csv(GetStringParameter(part, "WELD_" & key & "_FinalFillerConsumptionRate_kg_m")) & "," & _
              Csv(GetStringParameter(part, "WELD_" & key & "_EstimatedFillerConsumption_kg")) & "," & _
              Csv(ParameterOrDefault(part, key, "GasBottleVolume_L", "40")) & "," & _
              Csv(ParameterOrDefault(part, key, "GasBottlePressure_bar", "200")) & "," & _
              Csv(ParameterOrDefault(part, key, "GasPerBottle_L", "8000")) & "," & _
              Csv(ParameterOrDefault(part, key, "GasPerKgFiller_L", "400")) & "," & _
              Csv(GasLitersForRegister(part, key)) & "," & _
              Csv(GasBottlesForRegister(part, key)) & "," & _
              Csv(GetStringParameter(part, "WELD_" & key & "_VT")) & "," & _
              Csv(GetStringParameter(part, "WELD_" & key & "_PT")) & "," & _
              Csv(GetStringParameter(part, "WELD_" & key & "_UT")) & "," & _
              Csv(GetStringParameter(part, "WELD_" & key & "_Remark"))

        file.WriteLine row

    Next

    file.Close

    Dim summaryPath
    summaryPath = ExportWeldSummaryCSV(part, outputPath, weldIDs)

    If summaryPath <> "" Then
        MsgBox "Weld Register exported:" & vbCrLf & outputPath & vbCrLf & vbCrLf & _
               "Weld Summary exported:" & vbCrLf & summaryPath
    Else
        MsgBox "Weld Register exported:" & vbCrLf & outputPath
    End If

End Sub


Function ParameterOrDefault(part, weldKey, suffix, defaultValue)

    ParameterOrDefault = GetStringParameter(part, "WELD_" & weldKey & "_" & suffix)

    If Trim(CStr(ParameterOrDefault)) = "" Then
        ParameterOrDefault = CStr(defaultValue)
    End If

End Function


Function GasLitersForRegister(part, weldKey)

    Dim process
    process = SummaryValue(GetStringParameter(part, "WELD_" & weldKey & "_WeldingProcess"))

    If Trim(CStr(process)) = "111" Then
        GasLitersForRegister = "0"
        Exit Function
    End If

    Dim fillerKg
    fillerKg = ParseDecimalValue(GetStringParameter(part, "WELD_" & weldKey & "_EstimatedFillerConsumption_kg"))

    If CStr(fillerKg) = "" Then
        fillerKg = ParseDecimalValue(GetStringParameter(part, "WELD_" & weldKey & "_FillerConsumption_kg"))
    End If

    If IsGasShieldedWeldingProcess(process) And CStr(fillerKg) <> "" Then
        GasLitersForRegister = FormatEstimatedNumber(CDbl(fillerKg) * 400, 4)
        Exit Function
    End If

    Dim storedLiters
    storedLiters = ParseDecimalValue(GetStringParameter(part, "WELD_" & weldKey & "_EstimatedGasLiters"))

    If CStr(storedLiters) <> "" Then
        GasLitersForRegister = FormatEstimatedNumber(storedLiters, 4)
        Exit Function
    End If

    Dim storedBottles
    storedBottles = ParseDecimalValue(GetStringParameter(part, "WELD_" & weldKey & "_EstimatedGasBottles_40L_200bar"))

    If CStr(storedBottles) = "" Then
        storedBottles = ParseDecimalValue(GetStringParameter(part, "WELD_" & weldKey & "_EstimatedGasBottles_200bar"))
    End If

    If CStr(storedBottles) <> "" Then
        GasLitersForRegister = FormatEstimatedNumber(CDbl(storedBottles) * 8000, 4)
    Else
        GasLitersForRegister = "0"
    End If

End Function


Function GasBottlesForRegister(part, weldKey)

    Dim gasLiters
    gasLiters = ParseDecimalValue(GasLitersForRegister(part, weldKey))

    If CStr(gasLiters) = "" Then
        GasBottlesForRegister = "0"
    Else
        GasBottlesForRegister = FormatEstimatedNumber(CDbl(gasLiters) / 8000, 4)
    End If

End Function


Function ExportWeldSummaryCSV(part, registerPath, weldIDs)

    On Error Resume Next

    ExportWeldSummaryCSV = ""

    Dim fso
    Set fso = CreateObject("Scripting.FileSystemObject")

    Dim folderPath
    folderPath = fso.GetParentFolderName(registerPath)

    Dim summaryPath
    If folderPath = "" Then
        summaryPath = fso.GetBaseName(registerPath) & "_summary.csv"
    Else
        summaryPath = folderPath & "\" & fso.GetBaseName(registerPath) & "_summary.csv"
    End If

    Dim file
    Set file = fso.CreateTextFile(summaryPath, True)

    If Err.Number <> 0 Then
        Err.Clear
        ExportWeldSummaryCSV = ""
        On Error GoTo 0
        Exit Function
    End If

    Dim totalWelds
    totalWelds = 0

    Dim totalLengthM
    totalLengthM = 0

    Dim totalFillerKg
    totalFillerKg = 0

    Dim totalGasLiters
    totalGasLiters = 0

    Dim totalGasBottles
    totalGasBottles = 0

    Dim lengthByGroup
    Set lengthByGroup = CreateObject("Scripting.Dictionary")

    Dim fillerByGroup
    Set fillerByGroup = CreateObject("Scripting.Dictionary")

    Dim gasBottleByGroup
    Set gasBottleByGroup = CreateObject("Scripting.Dictionary")

    Dim gasLiterByGroup
    Set gasLiterByGroup = CreateObject("Scripting.Dictionary")

    Dim countByWeldType
    Set countByWeldType = CreateObject("Scripting.Dictionary")

    Dim countByWps
    Set countByWps = CreateObject("Scripting.Dictionary")

    Dim key
    For Each key In weldIDs.Keys

        totalWelds = totalWelds + 1

        Dim weldLengthM
        weldLengthM = ParseDecimalValue(GetStringParameter(part, "WELD_" & key & "_WeldLength_m"))

        If CStr(weldLengthM) = "" Then
            Dim weldLengthMm
            weldLengthMm = ParseDecimalValue(GetStringParameter(part, "WELD_" & key & "_WeldLength_mm"))

            If CStr(weldLengthMm) = "" Then
                weldLengthMm = ParseDecimalValue(GetStringParameter(part, "WELD_" & key & "_WeldLength"))
            End If

            If CStr(weldLengthMm) <> "" Then
                weldLengthM = CDbl(weldLengthMm) / 1000
            End If
        End If

        If CStr(weldLengthM) <> "" Then
            totalLengthM = totalLengthM + CDbl(weldLengthM)
        End If

        Dim fillerKg
        fillerKg = ParseDecimalValue(GetStringParameter(part, "WELD_" & key & "_EstimatedFillerConsumption_kg"))
        If CStr(fillerKg) = "" Then
            fillerKg = ParseDecimalValue(GetStringParameter(part, "WELD_" & key & "_FillerConsumption_kg"))
        End If

        If CStr(fillerKg) <> "" Then
            totalFillerKg = totalFillerKg + CDbl(fillerKg)
        End If

        Dim gasLiters
        gasLiters = ParseDecimalValue(GasLitersForRegister(part, key))

        If CStr(gasLiters) <> "" Then
            totalGasLiters = totalGasLiters + CDbl(gasLiters)
        End If

        Dim gasBottles
        gasBottles = ParseDecimalValue(GasBottlesForRegister(part, key))

        If CStr(gasBottles) <> "" Then
            totalGasBottles = totalGasBottles + CDbl(gasBottles)
        End If

        Dim weldType
        weldType = SummaryValue(GetStringParameter(part, "WELD_" & key & "_WeldType"))
        Call AddToDictionary(countByWeldType, weldType, 1)

        Dim wps
        wps = SummaryValue(GetStringParameter(part, "WELD_" & key & "_WPS"))
        Call AddToDictionary(countByWps, wps, 1)

        Dim process
        process = SummaryValue(GetStringParameter(part, "WELD_" & key & "_WeldingProcess"))

        Dim fillerTradeName
        fillerTradeName = SummaryValue(GetStringParameter(part, "WELD_" & key & "_FillerTradeName"))

        Dim fillerDesignation
        fillerDesignation = SummaryValue(GetStringParameter(part, "WELD_" & key & "_FillerDesignation"))

        Dim fillerDiameter
        fillerDiameter = SummaryValue(GetStringParameter(part, "WELD_" & key & "_FillerDiameter"))

        Dim groupKey
        groupKey = process & "|" & fillerTradeName & "|" & fillerDesignation & "|" & fillerDiameter & "|" & wps

        If Not lengthByGroup.Exists(groupKey) Then
            lengthByGroup.Add groupKey, 0
        End If

        If CStr(weldLengthM) <> "" Then
            Call AddToDictionary(lengthByGroup, groupKey, CDbl(weldLengthM))
        End If

        If CStr(fillerKg) <> "" Then
            Call AddToDictionary(fillerByGroup, groupKey, CDbl(fillerKg))
        End If

        If CStr(gasBottles) <> "" Then
            Call AddToDictionary(gasBottleByGroup, groupKey, CDbl(gasBottles))
        End If

        If CStr(gasLiters) <> "" Then
            Call AddToDictionary(gasLiterByGroup, groupKey, CDbl(gasLiters))
        End If

    Next

    file.WriteLine "SUMMARY_METRIC,VALUE"
    file.WriteLine Csv("TOTAL_WELDS") & "," & Csv(CStr(totalWelds))
    file.WriteLine Csv("TotalWeldLength_m") & "," & Csv(FormatEstimatedNumber(totalLengthM, 4))
    file.WriteLine Csv("TotalEstimatedFillerConsumption_kg") & "," & Csv(FormatEstimatedNumber(totalFillerKg, 4))
    file.WriteLine Csv("TotalEstimatedGasLiters") & "," & Csv(FormatEstimatedNumber(totalGasLiters, 4))
    file.WriteLine Csv("TotalEstimatedGasBottles_40L_200bar") & "," & Csv(FormatEstimatedNumber(totalGasBottles, 4))

    file.WriteLine ""
    file.WriteLine "TOTALS_BY_PROCESS_FILLER_AND_GAS"
    file.WriteLine "WeldingProcess,FillerTradeName,FillerDesignation,FillerDiameter,WPS,TotalWeldLength_m,TotalEstimatedFillerConsumption_kg,TotalEstimatedGasLiters,TotalEstimatedGasBottles_40L_200bar"

    Dim dictKey
    For Each dictKey In lengthByGroup.Keys
        Dim parts
        parts = Split(CStr(dictKey), "|")
        file.WriteLine Csv(parts(0)) & "," & _
                       Csv(parts(1)) & "," & _
                       Csv(parts(2)) & "," & _
                       Csv(parts(3)) & "," & _
                       Csv(parts(4)) & "," & _
                       Csv(FormatEstimatedNumber(DictionaryValue(lengthByGroup, dictKey), 4)) & "," & _
                       Csv(FormatEstimatedNumber(DictionaryValue(fillerByGroup, dictKey), 4)) & "," & _
                       Csv(FormatEstimatedNumber(DictionaryValue(gasLiterByGroup, dictKey), 4)) & "," & _
                       Csv(FormatEstimatedNumber(DictionaryValue(gasBottleByGroup, dictKey), 4))
    Next

    file.WriteLine ""
    file.WriteLine "TOTAL_WELDS_BY_WELDTYPE"
    file.WriteLine "WeldType,Count"

    For Each dictKey In countByWeldType.Keys
        file.WriteLine Csv(dictKey) & "," & Csv(CStr(countByWeldType.Item(dictKey)))
    Next

    file.WriteLine ""
    file.WriteLine "TOTAL_WELDS_BY_WPS"
    file.WriteLine "WPS,Count"

    For Each dictKey In countByWps.Keys
        file.WriteLine Csv(dictKey) & "," & Csv(CStr(countByWps.Item(dictKey)))
    Next

    file.Close

    If Err.Number = 0 Then
        ExportWeldSummaryCSV = summaryPath
    Else
        Err.Clear
        ExportWeldSummaryCSV = ""
    End If

    On Error GoTo 0

End Function


Function SummaryValue(value)

    SummaryValue = Trim(CStr(value))

    If SummaryValue = "" Then
        SummaryValue = "UNKNOWN"
    End If

End Function


Sub AddToDictionary(dict, key, amount)

    If dict.Exists(key) Then
        dict.Item(key) = CDbl(dict.Item(key)) + CDbl(amount)
    Else
        dict.Add key, CDbl(amount)
    End If

End Sub


Function DictionaryValue(dict, key)

    If dict.Exists(key) Then
        DictionaryValue = dict.Item(key)
    Else
        DictionaryValue = 0
    End If

End Function


Sub EnsureFolderExists(fso, folderPath)

    If folderPath = "" Then Exit Sub
    If fso.FolderExists(folderPath) Then Exit Sub

    Dim parentPath
    parentPath = fso.GetParentFolderName(folderPath)

    If parentPath <> "" Then
        If Not fso.FolderExists(parentPath) Then
            Call EnsureFolderExists(fso, parentPath)
        End If
    End If

    If Not fso.FolderExists(folderPath) Then
        fso.CreateFolder folderPath
    End If

End Sub


Function GetAllWeldIDs(part)

    Dim dict
    Set dict = CreateObject("Scripting.Dictionary")

    Dim params
    Set params = part.Parameters

    Dim i
    For i = 1 To params.Count

        Dim pName
        pName = CStr(params.Item(i).Name)

        If Left(UCase(pName), 6) = "WELD_W" Then

            Dim n
            n = ExtractWeldNumberFromText(pName)

            If n > 0 Then

                Dim weldID
                If n < 10 Then
                    weldID = "W00" & CStr(n)
                ElseIf n < 100 Then
                    weldID = "W0" & CStr(n)
                Else
                    weldID = "W" & CStr(n)
                End If

                If Not dict.Exists(weldID) Then
                    dict.Add weldID, weldID
                End If

            End If

        End If

    Next

    Set GetAllWeldIDs = dict

End Function


Function Csv(value)

    Dim s
    s = CStr(value)

    s = Replace(s, """", """""")
    s = Replace(s, vbCrLf, " ")
    s = Replace(s, vbCr, " ")
    s = Replace(s, vbLf, " ")

    Csv = """" & s & """"

End Function


' ==========================================================
' CATPRODUCT WELD_MAP PART SEARCH
' ==========================================================

Function GetActiveWeldMapPartFromProduct(productDoc)

    On Error Resume Next

    Dim rootProduct
    Set rootProduct = productDoc.Product

    Dim resultPart
    Set resultPart = Nothing

    Call FindWeldMapPartRecursive(rootProduct, resultPart)

    If resultPart Is Nothing Then
        Set GetActiveWeldMapPartFromProduct = Nothing
    Else
        Set GetActiveWeldMapPartFromProduct = resultPart
    End If

    On Error GoTo 0

End Function


Sub FindWeldMapPartRecursive(product, ByRef resultPart)

    On Error Resume Next

    Dim i
    For i = 1 To product.Products.Count

        Dim childProduct
        Set childProduct = product.Products.Item(i)

        If InStr(NormalizeName(childProduct.Name), "WELDMAP") > 0 Or _
           InStr(NormalizeName(childProduct.PartNumber), "WELDMAP") > 0 Then

            Dim refProduct
            Set refProduct = childProduct.ReferenceProduct

            Dim parentDoc
            Set parentDoc = refProduct.Parent

            If TypeName(parentDoc) = "PartDocument" Then
                Set resultPart = parentDoc.Part
                Exit Sub
            End If

        End If

        If childProduct.Products.Count > 0 Then
            Call FindWeldMapPartRecursive(childProduct, resultPart)

            If Not resultPart Is Nothing Then
                Exit Sub
            End If
        End If

    Next

    On Error GoTo 0

End Sub


Function NormalizeName(value)

    Dim s
    s = UCase(CStr(value))
    s = Replace(s, " ", "")
    s = Replace(s, "_", "")
    s = Replace(s, "-", "")

    NormalizeName = s

End Function
