Option Explicit

' ---------------------------------------------------------------------------
' ProbeSelectedWeldDesignObject.CATScript
'
' CATIA V5 Weld Design focused probe macro.
' The user selects exactly one Weld Design object in the CATIA tree and this
' macro writes a deep report for only that selected object.
'
' It does not scan the complete model, assign W001 IDs, create WPS data or edit
' the model. The goal is to learn whether the values visible in Fillet Weld
' Creation can be read from CATIA Automation.
' ---------------------------------------------------------------------------

Const MACRO_NAME = "ProbeSelectedWeldDesignObject"
Const REPORT_FILE_NAME = "selected_weld_design_object_probe.txt"

Sub CATMain()
    Dim doc
    Set doc = Nothing

    On Error Resume Next
    Set doc = CATIA.ActiveDocument
    On Error GoTo 0

    If doc Is Nothing Then
        MsgBox "Open CATProduct and select one Weld Design object.", vbExclamation, MACRO_NAME
        Exit Sub
    End If

    Dim sel
    Set sel = Nothing

    On Error Resume Next
    Set sel = doc.Selection
    On Error GoTo 0

    If sel Is Nothing Then
        MsgBox "Selection is not available in active document.", vbExclamation, MACRO_NAME
        Exit Sub
    End If

    Dim selectedCount
    selectedCount = SelectionCount(sel)

    If selectedCount <> 1 Then
        MsgBox "Select exactly one Weld Design object in CATIA tree and run macro again." & vbCrLf & _
               "Current selection count: " & CStr(selectedCount), vbExclamation, MACRO_NAME
        Exit Sub
    End If

    Dim selectedElement
    Dim selectedObj
    Set selectedElement = SelectionItem(sel, 1)
    Set selectedObj = SelectionItemValue(sel, 1)

    If selectedObj Is Nothing Then
        MsgBox "Selected object value is not accessible.", vbExclamation, MACRO_NAME
        Exit Sub
    End If

    Dim reportLines
    Set reportLines = NewList()

    ListAdd reportLines, "CATIA Weld Design selected object probe"
    ListAdd reportLines, "Active document: " & SafeDocumentName(doc)
    ListAdd reportLines, "Report file: " & REPORT_FILE_NAME
    ListAdd reportLines, ""
    ListAdd reportLines, "Purpose:"
    ListAdd reportLines, "  Probe one selected Weld Design object and check whether CATIA Automation"
    ListAdd reportLines, "  exposes values from Fillet Weld Creation tabs:"
    ListAdd reportLines, "  Parameters, Type, Material, Connection, Annotation."
    ListAdd reportLines, ""

    Call AppendSelectedObjectHeader(reportLines, doc, selectedElement, selectedObj)
    Call AppendMandatoryPropertyProbe(reportLines, selectedObj)
    Call AppendDirectPropertyProbe(reportLines, selectedObj)
    Call AppendAllParameters(reportLines, selectedObj, 800)
    Call AppendAllUserProperties(reportLines, selectedObj, 300)
    Call AppendAllRelations(reportLines, selectedObj, 300)
    Call AppendChildrenAndSubObjects(reportLines, selectedObj)
    Call AppendGeometryCollections(reportLines, selectedObj)
    Call AppendAnnotationProbe(reportLines, selectedObj)
    Call AppendReferencesSupportsLinks(reportLines, selectedObj)
    Call AppendWeldObjectFocus(reportLines, selectedObj)
    Call AppendWeldSymbolFocus(reportLines, selectedObj)
    Call AppendAssemblyJointFocus(reportLines, selectedObj)
    Call AppendOutputSummary(reportLines, selectedObj)

    Dim reportPath
    reportPath = WriteReportFile(doc, reportLines)

    MsgBox "Selected Weld Design object probe complete." & vbCrLf & _
           "Object: " & ObjectName(selectedObj) & vbCrLf & _
           "Report: " & reportPath, vbInformation, MACRO_NAME
End Sub

' ---------------------------------------------------------------------------
' Report sections
' ---------------------------------------------------------------------------

Sub AppendSelectedObjectHeader(reportLines, doc, selectedElement, selectedObj)
    ListAdd reportLines, "============================================================"
    ListAdd reportLines, "SELECTED OBJECT"
    ListAdd reportLines, "============================================================"
    ListAdd reportLines, "Selected object name: " & ObjectName(selectedObj)
    ListAdd reportLines, "TypeName: " & ObjectTypeName(selectedObj)
    ListAdd reportLines, "Parent path: " & ParentPath(selectedObj, 15)
    ListAdd reportLines, "Document path if available: " & FindDocumentFullPath(doc, selectedObj)
    ListAdd reportLines, "Raw display name candidates:"
    ListAdd reportLines, "  Object.Name: " & EmptyAsNotAccessible(ObjectName(selectedObj))
    ListAdd reportLines, "  Selection.Type: " & SelectionElementScalar(selectedElement, "Type")
    ListAdd reportLines, "  Selection.LeafProduct: " & SelectionElementObject(selectedElement, "LeafProduct")
    ListAdd reportLines, "  Parsed Part A / Part B from display name: " & ParsedPartPair(selectedObj)
    ListAdd reportLines, ""
End Sub

Sub AppendMandatoryPropertyProbe(reportLines, selectedObj)
    ListAdd reportLines, "============================================================"
    ListAdd reportLines, "MANDATORY PROPERTY NAMES"
    ListAdd reportLines, "============================================================"
    ListAdd reportLines, "Format: direct property | parameter search"
    ListAdd reportLines, "Note: names containing spaces or parentheses are not valid VBScript COM property identifiers;"
    ListAdd reportLines, "      they are still searched as parameter names."
    ListAdd reportLines, ""

    Dim names
    names = Array( _
        "Name", _
        "WeldName", _
        "Weld Name", _
        "Height", _
        "HeightC", _
        "Height_c", _
        "Height(c)", _
        "Size", _
        "WeldSize", _
        "PrimarySize", _
        "Shape", _
        "Offset", _
        "FirstLimit", _
        "SecondLimit", _
        "Type", _
        "Subtype", _
        "WeldType", _
        "Material", _
        "Connection", _
        "Annotation", _
        "Symbol", _
        "PrimarySymbol", _
        "Text", _
        "TextString", _
        "Value", _
        "String")

    Dim i
    Dim propName
    For i = LBound(names) To UBound(names)
        propName = CStr(names(i))
        ListAdd reportLines, "  " & propName & ": " & ProbeDirectAndParameter(selectedObj, propName)
    Next

    ListAdd reportLines, ""
End Sub

Sub AppendDirectPropertyProbe(reportLines, selectedObj)
    ListAdd reportLines, "============================================================"
    ListAdd reportLines, "ACCESSIBLE DIRECT PROPERTIES - BROAD PROBE"
    ListAdd reportLines, "============================================================"
    ListAdd reportLines, "CATIA Automation objects do not provide a reliable generic property enumerator in CATScript."
    ListAdd reportLines, "This section probes a broad list of likely direct property names."
    ListAdd reportLines, ""

    Dim names
    names = Array( _
        "Name", "PartNumber", "Nomenclature", "DescriptionRef", "DescriptionInst", _
        "Revision", "Definition", "Source", "InstanceName", _
        "WeldName", "WeldType", "WeldSize", "Height", "HeightC", "Height_c", _
        "Size", "PrimarySize", "PrimaryWeldSize", "Shape", "Offset", _
        "FirstLimit", "SecondLimit", "Type", "Subtype", "Material", _
        "Connection", "Annotation", "Symbol", "PrimarySymbol", "Text", _
        "TextString", "Value", "String", "Angle", "Orientation", _
        "X", "Y", "Z", "Length", "WeldLength", "Radius", "Diameter", _
        "Parent", "ReferenceProduct", "Part", "Product", "Reference", _
        "References", "Support", "Support1", "Support2", "Element", "Element1", _
        "Element2", "FirstPart", "SecondPart", "PartA", "PartB", _
        "ConnectedPartA", "ConnectedPartB", "Product1", "Product2", _
        "Component1", "Component2", "Leader", "LeaderTarget", "Target", _
        "AssociatedElement", "LinkedObject", "Geometry", "Anchor", _
        "AnnotationSet", "Leaders", "Texts", "Parameters", "Relations", _
        "Publications", "UserRefProperties", "Products", "Children", "Bodies", _
        "HybridBodies", "Shapes", "HybridShapes", "Sketches")

    Dim i
    Dim propName
    For i = LBound(names) To UBound(names)
        propName = CStr(names(i))
        ListAdd reportLines, "  " & propName & ": " & ProbeAnyProperty(selectedObj, propName)
    Next

    ListAdd reportLines, ""
End Sub

Sub AppendAllParameters(reportLines, selectedObj, limit)
    ListAdd reportLines, "============================================================"
    ListAdd reportLines, "ALL ACCESSIBLE PARAMETERS"
    ListAdd reportLines, "============================================================"

    Dim collections
    Set collections = NewList()
    Call AddParameterCollections(selectedObj, collections)

    If collections.Count = 0 Then
        ListAdd reportLines, "Parameters: not accessible"
        ListAdd reportLines, ""
        Exit Sub
    End If

    Dim i
    For i = 0 To collections.Count - 1
        ListAdd reportLines, "Parameter collection #" & CStr(i + 1)
        Call AppendParameterCollection(reportLines, collections.Item(i), limit)
        ListAdd reportLines, ""
    Next
End Sub

Sub AppendAllUserProperties(reportLines, selectedObj, limit)
    ListAdd reportLines, "============================================================"
    ListAdd reportLines, "ALL ACCESSIBLE USER PROPERTIES"
    ListAdd reportLines, "============================================================"

    Dim added
    added = 0
    added = added + AppendCollectionByPropertyWithReturn(reportLines, selectedObj, "UserRefProperties", limit)
    added = added + AppendReferenceProductCollectionByPropertyWithReturn(reportLines, selectedObj, "UserRefProperties", limit)
    added = added + AppendParentCollectionByPropertyWithReturn(reportLines, selectedObj, "UserRefProperties", limit, 5)

    Dim partObj
    Set partObj = PartObjectFrom(selectedObj)
    If Not partObj Is Nothing Then added = added + AppendCollectionByPropertyWithReturn(reportLines, partObj, "UserRefProperties", limit)

    If added = 0 Then ListAdd reportLines, "User properties: not accessible"
    ListAdd reportLines, ""
End Sub

Sub AppendAllRelations(reportLines, selectedObj, limit)
    ListAdd reportLines, "============================================================"
    ListAdd reportLines, "ALL ACCESSIBLE RELATIONS"
    ListAdd reportLines, "============================================================"

    Dim added
    added = 0
    added = added + AppendCollectionByPropertyWithReturn(reportLines, selectedObj, "Relations", limit)
    added = added + AppendReferenceProductCollectionByPropertyWithReturn(reportLines, selectedObj, "Relations", limit)
    added = added + AppendParentCollectionByPropertyWithReturn(reportLines, selectedObj, "Relations", limit, 5)

    Dim partObj
    Set partObj = PartObjectFrom(selectedObj)
    If Not partObj Is Nothing Then added = added + AppendCollectionByPropertyWithReturn(reportLines, partObj, "Relations", limit)

    If added = 0 Then ListAdd reportLines, "Relations: not accessible"
    ListAdd reportLines, ""
End Sub

Sub AppendChildrenAndSubObjects(reportLines, selectedObj)
    ListAdd reportLines, "============================================================"
    ListAdd reportLines, "ALL CHILDREN / SUBOBJECTS"
    ListAdd reportLines, "============================================================"

    Call AppendCollectionByProperty(reportLines, selectedObj, "Children", 300)
    Call AppendCollectionByProperty(reportLines, selectedObj, "Products", 300)
    Call AppendCollectionByProperty(reportLines, selectedObj, "Bodies", 300)
    Call AppendCollectionByProperty(reportLines, selectedObj, "HybridBodies", 300)
    Call AppendCollectionByProperty(reportLines, selectedObj, "Shapes", 300)
    Call AppendCollectionByProperty(reportLines, selectedObj, "HybridShapes", 300)
    Call AppendCollectionByProperty(reportLines, selectedObj, "Sketches", 300)
    Call AppendCollectionByProperty(reportLines, selectedObj, "AnnotationSets", 100)
    Call AppendCollectionByProperty(reportLines, selectedObj, "Annotations", 300)

    Dim partObj
    Set partObj = PartObjectFrom(selectedObj)
    If Not partObj Is Nothing Then
        ListAdd reportLines, ""
        ListAdd reportLines, "Part object children / subobjects:"
        Call AppendCollectionByProperty(reportLines, partObj, "Bodies", 500)
        Call AppendCollectionByProperty(reportLines, partObj, "HybridBodies", 500)
        Call AppendCollectionByProperty(reportLines, partObj, "OrderedGeometricalSets", 300)
        Call AppendCollectionByProperty(reportLines, partObj, "GeometricElements", 300)
        Call AppendCollectionByProperty(reportLines, partObj, "Relations", 300)
        Call AppendCollectionByProperty(reportLines, partObj, "Parameters", 500)
    End If

    ListAdd reportLines, ""
End Sub

Sub AppendGeometryCollections(reportLines, selectedObj)
    ListAdd reportLines, "============================================================"
    ListAdd reportLines, "BODIES / HYBRID BODIES / SHAPES IF APPLICABLE"
    ListAdd reportLines, "============================================================"

    Call AppendCollectionByProperty(reportLines, selectedObj, "Bodies", 500)
    Call AppendCollectionByProperty(reportLines, selectedObj, "HybridBodies", 500)
    Call AppendCollectionByProperty(reportLines, selectedObj, "Shapes", 500)
    Call AppendCollectionByProperty(reportLines, selectedObj, "HybridShapes", 500)
    Call AppendCollectionByProperty(reportLines, selectedObj, "Sketches", 300)
    Call AppendCollectionByProperty(reportLines, selectedObj, "GeometricElements", 300)

    Dim partObj
    Set partObj = PartObjectFrom(selectedObj)
    If Not partObj Is Nothing Then
        ListAdd reportLines, ""
        ListAdd reportLines, "Resolved Part object: " & DescribeModelObject(partObj)
        Call AppendCollectionByProperty(reportLines, partObj, "Bodies", 500)
        Call AppendCollectionByProperty(reportLines, partObj, "HybridBodies", 500)
        Call AppendCollectionByProperty(reportLines, partObj, "OrderedGeometricalSets", 300)
        Call AppendCollectionByProperty(reportLines, partObj, "GeometricElements", 300)
    Else
        ListAdd reportLines, "Resolved Part object: not accessible"
    End If

    ListAdd reportLines, ""
End Sub

Sub AppendAnnotationProbe(reportLines, selectedObj)
    ListAdd reportLines, "============================================================"
    ListAdd reportLines, "ANNOTATION FIELDS / LEADERS / TARGETS IF APPLICABLE"
    ListAdd reportLines, "============================================================"
    ListAdd reportLines, "Annotation field probes:"
    Call AppendNamedProbe(reportLines, selectedObj, "Text")
    Call AppendNamedProbe(reportLines, selectedObj, "TextString")
    Call AppendNamedProbe(reportLines, selectedObj, "String")
    Call AppendNamedProbe(reportLines, selectedObj, "Value")
    Call AppendNamedProbe(reportLines, selectedObj, "Symbol")
    Call AppendNamedProbe(reportLines, selectedObj, "PrimarySymbol")
    Call AppendNamedProbe(reportLines, selectedObj, "PrimarySize")
    Call AppendNamedProbe(reportLines, selectedObj, "PrimaryWeldSize")
    Call AppendNamedProbe(reportLines, selectedObj, "WeldType")
    Call AppendNamedProbe(reportLines, selectedObj, "Annotation")
    Call AppendNamedProbe(reportLines, selectedObj, "AnnotationSet")
    ListAdd reportLines, ""

    ListAdd reportLines, "Leaders / targets:"
    Call AppendCollectionByProperty(reportLines, selectedObj, "Leaders", 100)
    Call AppendNamedProbe(reportLines, selectedObj, "Leader")
    Call AppendNamedProbe(reportLines, selectedObj, "LeaderTarget")
    Call AppendNamedProbe(reportLines, selectedObj, "Target")
    Call AppendNamedProbe(reportLines, selectedObj, "AssociatedElement")
    Call AppendNamedProbe(reportLines, selectedObj, "LinkedObject")
    Call AppendNamedProbe(reportLines, selectedObj, "Support")
    Call AppendNamedProbe(reportLines, selectedObj, "Geometry")
    Call AppendNamedProbe(reportLines, selectedObj, "Anchor")
    ListAdd reportLines, ""
End Sub

Sub AppendReferencesSupportsLinks(reportLines, selectedObj)
    ListAdd reportLines, "============================================================"
    ListAdd reportLines, "REFERENCES / SUPPORTS / LINKS IF ACCESSIBLE"
    ListAdd reportLines, "============================================================"

    Dim names
    names = Array( _
        "Reference", "References", "ReferenceProduct", "Parent", _
        "Support", "Support1", "Support2", "Supports", _
        "Element", "Element1", "Element2", "Elements", _
        "FirstLimit", "SecondLimit", "Limit1", "Limit2", _
        "PartA", "PartB", "ConnectedPartA", "ConnectedPartB", _
        "FirstPart", "SecondPart", "Product1", "Product2", _
        "Component1", "Component2", "Connection", "Material", _
        "SelectedElements", "SelectedGeometries", "GeometricElements", _
        "AssociatedElement", "LinkedObject", "Target", "LeaderTarget", _
        "Annotation", "AnnotationSet")

    Dim i
    For i = LBound(names) To UBound(names)
        Call AppendNamedProbe(reportLines, selectedObj, CStr(names(i)))
    Next

    ListAdd reportLines, ""
End Sub

Sub AppendWeldObjectFocus(reportLines, selectedObj)
    Dim textValue
    textValue = UCase(ObjectName(selectedObj) & " " & ObjectTypeName(selectedObj))

    If InStr(textValue, "WELD") = 0 Then Exit Sub
    If InStr(textValue, "WELD SYMBOL") > 0 Then Exit Sub

    ListAdd reportLines, "============================================================"
    ListAdd reportLines, "SPECIAL PROBE - SELECTED WELD OBJECT"
    ListAdd reportLines, "============================================================"
    ListAdd reportLines, "Weld Name: " & FirstReadableValue(selectedObj, Array("WeldName", "Weld Name", "Name"))
    ListAdd reportLines, "Height(c): " & FirstReadableValue(selectedObj, Array("Height(c)", "HeightC", "Height_c", "Height", "Size", "WeldSize"))
    ListAdd reportLines, "Shape: " & FirstReadableValue(selectedObj, Array("Shape"))
    ListAdd reportLines, "Offset: " & FirstReadableValue(selectedObj, Array("Offset"))
    ListAdd reportLines, "First Limit: " & FirstReadableValue(selectedObj, Array("FirstLimit", "First Limit", "Limit1", "Support1", "Element1"))
    ListAdd reportLines, "Second Limit: " & FirstReadableValue(selectedObj, Array("SecondLimit", "Second Limit", "Limit2", "Support2", "Element2"))
    ListAdd reportLines, ""
    ListAdd reportLines, "Selected geometric elements:"
    Call AppendNamedProbe(reportLines, selectedObj, "SelectedElements")
    Call AppendNamedProbe(reportLines, selectedObj, "SelectedGeometries")
    Call AppendNamedProbe(reportLines, selectedObj, "GeometricElements")
    Call AppendNamedProbe(reportLines, selectedObj, "Elements")
    Call AppendNamedProbe(reportLines, selectedObj, "Element1")
    Call AppendNamedProbe(reportLines, selectedObj, "Element2")
    Call AppendNamedProbe(reportLines, selectedObj, "Support1")
    Call AppendNamedProbe(reportLines, selectedObj, "Support2")
    ListAdd reportLines, ""
    ListAdd reportLines, "Connected surfaces/components:"
    Call AppendNamedProbe(reportLines, selectedObj, "Connection")
    Call AppendNamedProbe(reportLines, selectedObj, "PartA")
    Call AppendNamedProbe(reportLines, selectedObj, "PartB")
    Call AppendNamedProbe(reportLines, selectedObj, "ConnectedPartA")
    Call AppendNamedProbe(reportLines, selectedObj, "ConnectedPartB")
    Call AppendNamedProbe(reportLines, selectedObj, "FirstPart")
    Call AppendNamedProbe(reportLines, selectedObj, "SecondPart")
    ListAdd reportLines, ""
End Sub

Sub AppendWeldSymbolFocus(reportLines, selectedObj)
    Dim textValue
    textValue = UCase(ObjectName(selectedObj) & " " & ObjectTypeName(selectedObj))

    If InStr(textValue, "WELD SYMBOL") = 0 And InStr(textValue, "ANNOTATION") = 0 Then Exit Sub

    ListAdd reportLines, "============================================================"
    ListAdd reportLines, "SPECIAL PROBE - SELECTED WELD SYMBOL"
    ListAdd reportLines, "============================================================"
    ListAdd reportLines, "symbol text: " & FirstReadableValue(selectedObj, Array("Text", "TextString", "String", "Value"))
    ListAdd reportLines, "primary size: " & FirstReadableValue(selectedObj, Array("PrimarySize", "PrimaryWeldSize", "Size", "WeldSize"))
    ListAdd reportLines, "leader target: " & FirstReadableValue(selectedObj, Array("LeaderTarget", "Target", "AssociatedElement", "LinkedObject"))
    ListAdd reportLines, "associated weld object: " & FirstReadableValue(selectedObj, Array("AssociatedElement", "LinkedObject", "Reference", "Target"))
    ListAdd reportLines, "associated assembly joint: " & FirstReadableValue(selectedObj, Array("AssemblyJoint", "Joint", "Connection", "Reference"))
    ListAdd reportLines, "annotation set: " & FirstReadableValue(selectedObj, Array("AnnotationSet", "Parent"))
    ListAdd reportLines, ""
    Call AppendCollectionByProperty(reportLines, selectedObj, "Leaders", 100)
    Call AppendCollectionByProperty(reportLines, selectedObj, "Texts", 100)
    ListAdd reportLines, ""
End Sub

Sub AppendAssemblyJointFocus(reportLines, selectedObj)
    Dim textValue
    textValue = UCase(ObjectName(selectedObj) & " " & ObjectTypeName(selectedObj))

    If InStr(textValue, "ASSEMBLY JOINT") = 0 And InStr(textValue, "ASSEMBLYJOINT") = 0 And InStr(textValue, "JOINT") = 0 Then Exit Sub

    ListAdd reportLines, "============================================================"
    ListAdd reportLines, "SPECIAL PROBE - SELECTED ASSEMBLY JOINT"
    ListAdd reportLines, "============================================================"
    ListAdd reportLines, "raw display name: " & ObjectName(selectedObj)
    ListAdd reportLines, "connected Part A: " & EmptyAsNotAccessible(CandidatePartA(selectedObj))
    ListAdd reportLines, "connected Part B: " & EmptyAsNotAccessible(CandidatePartB(selectedObj))
    ListAdd reportLines, "parsed from display name: " & ParsedPartPair(selectedObj)
    ListAdd reportLines, ""
    ListAdd reportLines, "Expected children checks:"
    Call AppendCollectionByProperty(reportLines, selectedObj, "Children", 200)
    Call AppendCollectionByProperty(reportLines, selectedObj, "Products", 200)
    Call AppendCollectionByProperty(reportLines, selectedObj, "Bodies", 200)
    Call AppendCollectionByProperty(reportLines, selectedObj, "HybridBodies", 200)
    Call AppendNamedProbe(reportLines, selectedObj, "JointBody")
    Call AppendNamedProbe(reportLines, selectedObj, "Weld")
    Call AppendNamedProbe(reportLines, selectedObj, "WeldSymbol")
    Call AppendNamedProbe(reportLines, selectedObj, "NewMaterial")
    Call AppendNamedProbe(reportLines, selectedObj, "Material")
    ListAdd reportLines, ""
End Sub

Sub AppendOutputSummary(reportLines, selectedObj)
    ListAdd reportLines, "============================================================"
    ListAdd reportLines, "OUTPUT SUMMARY"
    ListAdd reportLines, "============================================================"
    ListAdd reportLines, "Readable Weld Name: " & YesNo(HasReadableValue(selectedObj, Array("WeldName", "Weld Name")))
    ListAdd reportLines, "Readable Height(c): " & YesNo(HasReadableValue(selectedObj, Array("Height(c)", "HeightC", "Height_c", "Height")))
    ListAdd reportLines, "Readable Weld Size: " & YesNo(HasReadableValue(selectedObj, Array("WeldSize", "Size", "PrimarySize", "PrimaryWeldSize", "Height(c)", "Height")))
    ListAdd reportLines, "Readable Shape: " & YesNo(HasReadableValue(selectedObj, Array("Shape")))
    ListAdd reportLines, "Readable connected surfaces/components: " & YesNo(HasConnectedSurfaceOrComponent(selectedObj))
    ListAdd reportLines, "Readable Weld Symbol text: " & YesNo(HasReadableValue(selectedObj, Array("Text", "TextString", "Value", "String")))
    ListAdd reportLines, "Readable leader/target: " & YesNo(HasLeaderOrTarget(selectedObj))
    ListAdd reportLines, "Readable PartA/PartB: " & YesNo(HasPartAOrPartB(selectedObj))
    ListAdd reportLines, ""
End Sub

Sub AppendNamedProbe(reportLines, selectedObj, propertyName)
    ListAdd reportLines, "  " & CStr(propertyName) & ": " & ProbeAnyProperty(selectedObj, CStr(propertyName))
End Sub

' ---------------------------------------------------------------------------
' Candidate values and summary checks
' ---------------------------------------------------------------------------

Function FirstReadableValue(obj, names)
    Dim i
    Dim value

    FirstReadableValue = "not accessible"

    For i = LBound(names) To UBound(names)
        value = CombinedReadableValue(obj, CStr(names(i)))
        If IsReadableText(value) Then
            FirstReadableValue = value
            Exit Function
        End If
    Next
End Function

Function HasReadableValue(obj, names)
    Dim i
    Dim value

    HasReadableValue = False
    For i = LBound(names) To UBound(names)
        value = CombinedReadableValue(obj, CStr(names(i)))
        If IsReadableText(value) Then
            HasReadableValue = True
            Exit Function
        End If
    Next
End Function

Function HasConnectedSurfaceOrComponent(obj)
    HasConnectedSurfaceOrComponent = HasReadableValue(obj, Array( _
        "Connection", "SelectedElements", "SelectedGeometries", "GeometricElements", _
        "Elements", "Element1", "Element2", "Support1", "Support2", _
        "PartA", "PartB", "ConnectedPartA", "ConnectedPartB", "FirstPart", "SecondPart"))
End Function

Function HasLeaderOrTarget(obj)
    HasLeaderOrTarget = False

    If HasReadableValue(obj, Array("LeaderTarget", "Target", "AssociatedElement", "LinkedObject", "Leader")) Then
        HasLeaderOrTarget = True
        Exit Function
    End If

    Dim ok
    Dim errText
    Dim leaders
    Set leaders = ObjectProperty(obj, "Leaders", ok, errText)
    If ok And Not leaders Is Nothing Then
        If CollectionCount(leaders) > 0 Then HasLeaderOrTarget = True
    End If
End Function

Function HasPartAOrPartB(obj)
    HasPartAOrPartB = False

    If CandidatePartA(obj) <> "" Or CandidatePartB(obj) <> "" Then
        HasPartAOrPartB = True
        Exit Function
    End If

    If ParsedPartPair(obj) <> "not found" Then HasPartAOrPartB = True
End Function

Function CandidatePartA(obj)
    CandidatePartA = FirstNonEmpty(Array( _
        ObjectDescriptionFromObjectProperty(obj, "PartA"), _
        ObjectDescriptionFromObjectProperty(obj, "ConnectedPartA"), _
        ObjectDescriptionFromObjectProperty(obj, "FirstPart"), _
        ObjectDescriptionFromObjectProperty(obj, "Reference1"), _
        ObjectDescriptionFromObjectProperty(obj, "Support1"), _
        ObjectDescriptionFromObjectProperty(obj, "Element1"), _
        ObjectDescriptionFromObjectProperty(obj, "Product1"), _
        ObjectDescriptionFromObjectProperty(obj, "Component1"), _
        ParameterValueByKeywords(obj, Array("PartA", "ConnectedPartA", "FirstPart", "Reference1", "Support1", "Element1"))))
End Function

Function CandidatePartB(obj)
    CandidatePartB = FirstNonEmpty(Array( _
        ObjectDescriptionFromObjectProperty(obj, "PartB"), _
        ObjectDescriptionFromObjectProperty(obj, "ConnectedPartB"), _
        ObjectDescriptionFromObjectProperty(obj, "SecondPart"), _
        ObjectDescriptionFromObjectProperty(obj, "Reference2"), _
        ObjectDescriptionFromObjectProperty(obj, "Support2"), _
        ObjectDescriptionFromObjectProperty(obj, "Element2"), _
        ObjectDescriptionFromObjectProperty(obj, "Product2"), _
        ObjectDescriptionFromObjectProperty(obj, "Component2"), _
        ParameterValueByKeywords(obj, Array("PartB", "ConnectedPartB", "SecondPart", "Reference2", "Support2", "Element2"))))
End Function

Function ObjectDescriptionFromObjectProperty(obj, propertyName)
    Dim refObj
    Dim ok
    Dim errText

    Set refObj = ObjectProperty(obj, CStr(propertyName), ok, errText)
    If ok And Not refObj Is Nothing Then
        ObjectDescriptionFromObjectProperty = DescribeModelObject(refObj)
    Else
        ObjectDescriptionFromObjectProperty = ""
    End If
End Function

Function ParsedPartPair(obj)
    Dim candidates
    candidates = Array(ObjectName(obj), ParentPath(obj, 4))

    Dim i
    Dim s
    Dim a
    Dim b
    Dim openPos
    Dim closePos
    Dim innerText
    Dim pieces

    ParsedPartPair = "not found"

    For i = LBound(candidates) To UBound(candidates)
        s = CStr(candidates(i))
        openPos = InStr(s, "(")
        closePos = InStrRev(s, ")")

        If openPos > 0 And closePos > openPos Then
            innerText = Mid(s, openPos + 1, closePos - openPos - 1)
            pieces = Split(innerText, ",")
            If UBound(pieces) >= 1 Then
                a = Trim(CStr(pieces(0)))
                b = Trim(CStr(pieces(1)))
                If a <> "" Or b <> "" Then
                    ParsedPartPair = "Part A=" & a & " | Part B=" & b
                    Exit Function
                End If
            End If
        End If
    Next
End Function

' ---------------------------------------------------------------------------
' Property and parameter probing
' ---------------------------------------------------------------------------

Function ProbeDirectAndParameter(obj, propertyName)
    Dim directValue
    Dim paramValue

    directValue = ProbeAnyProperty(obj, propertyName)
    paramValue = ParameterValueByKeywords(obj, Array(propertyName))

    If paramValue = "" Then paramValue = "not accessible"

    ProbeDirectAndParameter = "direct=" & directValue & " | parameter=" & paramValue
End Function

Function CombinedReadableValue(obj, propertyName)
    Dim directValue
    Dim paramValue

    directValue = ProbeAnyProperty(obj, propertyName)
    If IsReadableText(directValue) Then
        CombinedReadableValue = directValue
        Exit Function
    End If

    paramValue = ParameterValueByKeywords(obj, Array(propertyName))
    If IsReadableText(paramValue) Then
        CombinedReadableValue = paramValue
    Else
        CombinedReadableValue = ""
    End If
End Function

Function ProbeAnyProperty(obj, propertyName)
    Dim ok
    Dim errText
    Dim refObj

    If Not IsAutomationIdentifier(propertyName) Then
        ProbeAnyProperty = "not accessible"
        Exit Function
    End If

    Set refObj = ObjectProperty(obj, propertyName, ok, errText)
    If ok And Not refObj Is Nothing Then
        If CollectionCount(refObj) > 0 Then
            ProbeAnyProperty = "collection/object: " & DescribeModelObject(refObj) & " | Count=" & CStr(CollectionCount(refObj))
        Else
            ProbeAnyProperty = DescribeModelObject(refObj)
        End If
        Exit Function
    End If

    Dim scalarValue
    scalarValue = ScalarProperty(obj, propertyName, ok, errText)
    If ok Then
        If scalarValue = "" Then
            ProbeAnyProperty = "<empty>"
        Else
            ProbeAnyProperty = scalarValue
        End If
    Else
        ProbeAnyProperty = "not accessible"
    End If
End Function

Function ScalarProperty(obj, propertyName, ByRef ok, ByRef errText)
    ok = False
    errText = ""
    ScalarProperty = ""

    If Not IsAutomationIdentifier(propertyName) Then Exit Function

    On Error Resume Next
    Dim v
    v = Eval("obj." & CStr(propertyName))
    If Err.Number = 0 Then
        ok = True
        ScalarProperty = ScalarToString(v)
    Else
        errText = Err.Description
        Err.Clear
    End If
    On Error GoTo 0
End Function

Function ObjectProperty(obj, propertyName, ByRef ok, ByRef errText)
    ok = False
    errText = ""

    Dim tmpObj
    Set tmpObj = Nothing

    If Not IsAutomationIdentifier(propertyName) Then
        Set ObjectProperty = Nothing
        Exit Function
    End If

    On Error Resume Next
    Execute "Set tmpObj = obj." & CStr(propertyName)
    If Err.Number = 0 Then
        If Not tmpObj Is Nothing Then ok = True
    Else
        errText = Err.Description
        Err.Clear
    End If
    On Error GoTo 0

    Set ObjectProperty = tmpObj
End Function

Function ParameterValueByKeywords(obj, keywords)
    ParameterValueByKeywords = ""

    Dim collections
    Set collections = NewList()
    Call AddParameterCollections(obj, collections)

    Dim c
    Dim params
    Dim value

    For c = 0 To collections.Count - 1
        Set params = collections.Item(c)
        value = ParameterValueFromCollection(params, keywords)
        If value <> "" Then
            ParameterValueByKeywords = value
            Exit Function
        End If
    Next
End Function

Function ParameterValueFromCollection(params, keywords)
    ParameterValueFromCollection = ""

    If params Is Nothing Then Exit Function

    Dim i
    Dim p
    Dim pName
    Dim k
    Dim wanted

    On Error Resume Next
    For i = 1 To params.Count
        Set p = Nothing
        Set p = params.Item(i)
        If Err.Number = 0 And Not p Is Nothing Then
            pName = NormalizeName(ObjectName(p))
            For k = LBound(keywords) To UBound(keywords)
                wanted = NormalizeName(CStr(keywords(k)))
                If wanted <> "" Then
                    If pName = wanted Or InStr(pName, wanted) > 0 Then
                        ParameterValueFromCollection = ObjectName(p) & " = " & ParameterDisplayValue(p)
                        If ParameterValueFromCollection <> "" Then
                            On Error GoTo 0
                            Exit Function
                        End If
                    End If
                End If
            Next
        End If
        Err.Clear
    Next
    On Error GoTo 0
End Function

Sub AddParameterCollections(obj, collections)
    Call AddCollectionIfAccessible(collections, obj, "Parameters")
    Call AddReferenceProductCollectionIfAccessible(collections, obj, "Parameters")
    Call AddParentCollectionIfAccessible(collections, obj, "Parameters", 5)

    Dim partObj
    Set partObj = PartObjectFrom(obj)
    If Not partObj Is Nothing Then Call AddCollectionIfAccessible(collections, partObj, "Parameters")
End Sub

' ---------------------------------------------------------------------------
' Collection reporting
' ---------------------------------------------------------------------------

Sub AppendParameterCollection(reportLines, params, limit)
    If params Is Nothing Then
        ListAdd reportLines, "  not accessible"
        Exit Sub
    End If

    Dim countValue
    countValue = CollectionCount(params)
    ListAdd reportLines, "  Count: " & CStr(countValue)

    If countValue = 0 Then Exit Sub

    Dim maxItems
    maxItems = limit
    If countValue < maxItems Then maxItems = countValue

    Dim i
    Dim p
    For i = 1 To maxItems
        Set p = CollectionItem(params, i)
        If Not p Is Nothing Then
            ListAdd reportLines, "  - " & ObjectName(p) & " [" & ObjectTypeName(p) & "] = " & ParameterDisplayValue(p)
        Else
            ListAdd reportLines, "  - item " & CStr(i) & ": not accessible"
        End If
    Next

    If countValue > maxItems Then ListAdd reportLines, "  ... truncated after " & CStr(maxItems) & " items"
End Sub

Sub AppendCollectionByProperty(reportLines, obj, propertyName, limit)
    Dim dummy
    dummy = AppendCollectionByPropertyWithReturn(reportLines, obj, propertyName, limit)
End Sub

Function AppendCollectionByPropertyWithReturn(reportLines, obj, propertyName, limit)
    AppendCollectionByPropertyWithReturn = 0

    Dim ok
    Dim errText
    Dim collectionObj
    Set collectionObj = ObjectProperty(obj, CStr(propertyName), ok, errText)

    If Not ok Or collectionObj Is Nothing Then
        ListAdd reportLines, "  " & propertyName & ": not accessible"
        Exit Function
    End If

    ListAdd reportLines, "  " & propertyName & ":"
    Call AppendGenericCollection(reportLines, collectionObj, limit)
    AppendCollectionByPropertyWithReturn = 1
End Function

Function AppendReferenceProductCollectionByPropertyWithReturn(reportLines, obj, propertyName, limit)
    AppendReferenceProductCollectionByPropertyWithReturn = 0

    Dim refObj
    Dim ok
    Dim errText
    Set refObj = ObjectProperty(obj, "ReferenceProduct", ok, errText)

    If Not ok Or refObj Is Nothing Then Exit Function

    ListAdd reportLines, "  ReferenceProduct." & propertyName & ":"
    AppendReferenceProductCollectionByPropertyWithReturn = AppendCollectionByPropertyWithReturn(reportLines, refObj, propertyName, limit)
End Function

Function AppendParentCollectionByPropertyWithReturn(reportLines, obj, propertyName, limit, maxDepth)
    AppendParentCollectionByPropertyWithReturn = 0

    Dim current
    Dim depth
    Set current = ObjectParent(obj)
    depth = 0

    Do While Not current Is Nothing And depth < maxDepth
        ListAdd reportLines, "  Parent level " & CStr(depth + 1) & " (" & DescribeModelObject(current) & ")." & propertyName & ":"
        AppendParentCollectionByPropertyWithReturn = AppendParentCollectionByPropertyWithReturn + AppendCollectionByPropertyWithReturn(reportLines, current, propertyName, limit)
        Set current = ObjectParent(current)
        depth = depth + 1
    Loop
End Function

Sub AppendGenericCollection(reportLines, collectionObj, limit)
    Dim countValue
    countValue = CollectionCount(collectionObj)
    ListAdd reportLines, "    Count: " & CStr(countValue)

    If countValue = 0 Then Exit Sub

    Dim maxItems
    maxItems = limit
    If countValue < maxItems Then maxItems = countValue

    Dim i
    Dim itemObj
    For i = 1 To maxItems
        Set itemObj = CollectionItem(collectionObj, i)
        If Not itemObj Is Nothing Then
            ListAdd reportLines, "    - " & DescribeModelObject(itemObj) & " | Value: " & GenericDisplayValue(itemObj)
        Else
            ListAdd reportLines, "    - item " & CStr(i) & ": not accessible"
        End If
    Next

    If countValue > maxItems Then ListAdd reportLines, "    ... truncated after " & CStr(maxItems) & " items"
End Sub

Sub AddCollectionIfAccessible(collections, obj, propertyName)
    Dim ok
    Dim errText
    Dim collectionObj
    Set collectionObj = ObjectProperty(obj, propertyName, ok, errText)
    If ok And Not collectionObj Is Nothing Then collections.Add collectionObj
End Sub

Sub AddReferenceProductCollectionIfAccessible(collections, obj, propertyName)
    Dim ok
    Dim errText
    Dim refObj
    Set refObj = ObjectProperty(obj, "ReferenceProduct", ok, errText)
    If ok And Not refObj Is Nothing Then Call AddCollectionIfAccessible(collections, refObj, propertyName)
End Sub

Sub AddParentCollectionIfAccessible(collections, obj, propertyName, maxDepth)
    Dim current
    Dim depth
    Set current = ObjectParent(obj)
    depth = 0

    Do While Not current Is Nothing And depth < maxDepth
        Call AddCollectionIfAccessible(collections, current, propertyName)
        Set current = ObjectParent(current)
        depth = depth + 1
    Loop
End Sub

' ---------------------------------------------------------------------------
' Object / CATIA helpers
' ---------------------------------------------------------------------------

Function SelectionCount(sel)
    SelectionCount = 0

    On Error Resume Next
    SelectionCount = CLng(sel.Count2)
    If Err.Number <> 0 Then
        Err.Clear
        SelectionCount = CLng(sel.Count)
    End If
    If Err.Number <> 0 Then
        Err.Clear
        SelectionCount = 0
    End If
    On Error GoTo 0
End Function

Function SelectionItem(sel, indexValue)
    Set SelectionItem = Nothing

    On Error Resume Next
    Set SelectionItem = sel.Item2(CLng(indexValue))
    If Err.Number <> 0 Then
        Err.Clear
        Set SelectionItem = sel.Item(CLng(indexValue))
    End If
    If Err.Number <> 0 Then
        Err.Clear
        Set SelectionItem = Nothing
    End If
    On Error GoTo 0
End Function

Function SelectionItemValue(sel, indexValue)
    Set SelectionItemValue = Nothing

    Dim itemObj
    Set itemObj = SelectionItem(sel, indexValue)
    If itemObj Is Nothing Then Exit Function

    On Error Resume Next
    Set SelectionItemValue = itemObj.Value
    If Err.Number <> 0 Then
        Err.Clear
        Set SelectionItemValue = Nothing
    End If
    On Error GoTo 0
End Function

Function SelectionElementScalar(selectionElement, propertyName)
    SelectionElementScalar = "not accessible"
    If selectionElement Is Nothing Then Exit Function

    Dim ok
    Dim errText
    Dim value
    value = ScalarProperty(selectionElement, propertyName, ok, errText)
    If ok Then
        If value = "" Then
            SelectionElementScalar = "<empty>"
        Else
            SelectionElementScalar = value
        End If
    End If
End Function

Function SelectionElementObject(selectionElement, propertyName)
    SelectionElementObject = "not accessible"
    If selectionElement Is Nothing Then Exit Function

    Dim ok
    Dim errText
    Dim obj
    Set obj = ObjectProperty(selectionElement, propertyName, ok, errText)
    If ok And Not obj Is Nothing Then SelectionElementObject = DescribeModelObject(obj)
End Function

Function ObjectParent(obj)
    Dim ok
    Dim errText
    Set ObjectParent = ObjectProperty(obj, "Parent", ok, errText)
End Function

Function ObjectName(obj)
    ObjectName = ""
    If obj Is Nothing Then Exit Function

    On Error Resume Next
    ObjectName = CStr(obj.Name)
    If Err.Number <> 0 Then
        Err.Clear
        ObjectName = CStr(obj.PartNumber)
    End If
    If Err.Number <> 0 Then
        Err.Clear
        ObjectName = "<unnamed>"
    End If
    On Error GoTo 0
End Function

Function ObjectTypeName(obj)
    ObjectTypeName = ""
    If obj Is Nothing Then
        ObjectTypeName = "<nothing>"
    Else
        On Error Resume Next
        ObjectTypeName = TypeName(obj)
        If Err.Number <> 0 Then
            Err.Clear
            ObjectTypeName = "<unknown>"
        End If
        On Error GoTo 0
    End If
End Function

Function DescribeModelObject(obj)
    If obj Is Nothing Then
        DescribeModelObject = "<nothing>"
        Exit Function
    End If

    Dim nameValue
    Dim typeValue
    Dim partNumber

    nameValue = ObjectName(obj)
    typeValue = ObjectTypeName(obj)
    partNumber = ProbeScalarOnly(obj, "PartNumber")

    If partNumber = "" Then
        Dim ok
        Dim errText
        Dim refObj
        Set refObj = ObjectProperty(obj, "ReferenceProduct", ok, errText)
        If ok And Not refObj Is Nothing Then partNumber = ProbeScalarOnly(refObj, "PartNumber")
    End If

    If partNumber <> "" Then
        DescribeModelObject = partNumber & " (" & typeValue & ": " & nameValue & ")"
    Else
        DescribeModelObject = typeValue & ": " & nameValue
    End If
End Function

Function ProbeScalarOnly(obj, propertyName)
    Dim ok
    Dim errText
    ProbeScalarOnly = ScalarProperty(obj, propertyName, ok, errText)
    If Not ok Then ProbeScalarOnly = ""
End Function

Function ParentPath(obj, maxDepth)
    ParentPath = ""
    If obj Is Nothing Then Exit Function

    Dim current
    Dim depth
    Dim piece
    Set current = obj
    depth = 0

    On Error Resume Next
    Do While Not current Is Nothing And depth < maxDepth
        piece = ObjectTypeName(current) & ":" & ObjectName(current)
        If ParentPath = "" Then
            ParentPath = piece
        Else
            ParentPath = piece & " > " & ParentPath
        End If
        Set current = current.Parent
        If Err.Number <> 0 Then
            Err.Clear
            Exit Do
        End If
        depth = depth + 1
    Loop
    On Error GoTo 0
End Function

Function FindDocumentFullPath(doc, obj)
    FindDocumentFullPath = ""

    On Error Resume Next
    FindDocumentFullPath = CStr(doc.FullName)
    If Err.Number <> 0 Then
        Err.Clear
        FindDocumentFullPath = ""
    End If
    On Error GoTo 0

    If FindDocumentFullPath <> "" Then Exit Function

    Dim current
    Dim depth
    Set current = obj
    depth = 0

    On Error Resume Next
    Do While Not current Is Nothing And depth < 15
        If TypeName(current) = "ProductDocument" Or TypeName(current) = "PartDocument" Then
            FindDocumentFullPath = CStr(current.FullName)
            If Err.Number = 0 And FindDocumentFullPath <> "" Then
                On Error GoTo 0
                Exit Function
            End If
            Err.Clear
        End If
        Set current = current.Parent
        If Err.Number <> 0 Then
            Err.Clear
            Exit Do
        End If
        depth = depth + 1
    Loop
    On Error GoTo 0

    If FindDocumentFullPath = "" Then FindDocumentFullPath = "not accessible"
End Function

Function PartObjectFrom(obj)
    Dim current
    Dim depth
    Dim ok
    Dim errText
    Dim partObj
    Dim refObj
    Dim parentDoc

    Set PartObjectFrom = Nothing
    Set current = obj
    depth = 0

    Do While Not current Is Nothing And depth < 10
        Set partObj = ObjectProperty(current, "Part", ok, errText)
        If ok And Not partObj Is Nothing Then
            Set PartObjectFrom = partObj
            Exit Function
        End If

        Set refObj = ObjectProperty(current, "ReferenceProduct", ok, errText)
        If ok And Not refObj Is Nothing Then
            Set parentDoc = ObjectParent(refObj)
            If Not parentDoc Is Nothing Then
                Set partObj = ObjectProperty(parentDoc, "Part", ok, errText)
                If ok And Not partObj Is Nothing Then
                    Set PartObjectFrom = partObj
                    Exit Function
                End If
            End If
        End If

        Set current = ObjectParent(current)
        depth = depth + 1
    Loop
End Function

Function CollectionCount(collectionObj)
    CollectionCount = 0
    If collectionObj Is Nothing Then Exit Function

    On Error Resume Next
    CollectionCount = CLng(collectionObj.Count)
    If Err.Number <> 0 Then
        Err.Clear
        CollectionCount = 0
    End If
    On Error GoTo 0
End Function

Function CollectionItem(collectionObj, indexValue)
    Set CollectionItem = Nothing
    If collectionObj Is Nothing Then Exit Function

    On Error Resume Next
    Set CollectionItem = collectionObj.Item(CLng(indexValue))
    If Err.Number <> 0 Then
        Err.Clear
        Set CollectionItem = Nothing
    End If
    On Error GoTo 0
End Function

' ---------------------------------------------------------------------------
' Display helpers
' ---------------------------------------------------------------------------

Function ParameterDisplayValue(parameterObj)
    ParameterDisplayValue = GenericDisplayValue(parameterObj)
End Function

Function GenericDisplayValue(obj)
    GenericDisplayValue = FirstNonEmpty(Array( _
        ProbeScalarOnly(obj, "ValueAsString"), _
        ProbeScalarOnly(obj, "Value"), _
        ProbeScalarOnly(obj, "Magnitude"), _
        ProbeScalarOnly(obj, "Formula"), _
        ProbeScalarOnly(obj, "Comment"), _
        ProbeScalarOnly(obj, "Definition"), _
        ProbeScalarOnly(obj, "DescriptionRef")))
End Function

Function ScalarToString(value)
    On Error Resume Next
    If IsNull(value) Then
        ScalarToString = ""
    ElseIf IsEmpty(value) Then
        ScalarToString = ""
    ElseIf VarType(value) = 11 Then
        If CBool(value) Then
            ScalarToString = "True"
        Else
            ScalarToString = "False"
        End If
    Else
        ScalarToString = CStr(value)
    End If
    If Err.Number <> 0 Then
        Err.Clear
        ScalarToString = ""
    End If
    On Error GoTo 0
End Function

Function EmptyAsNotAccessible(value)
    If Trim(CStr(value)) = "" Then
        EmptyAsNotAccessible = "not accessible"
    Else
        EmptyAsNotAccessible = CStr(value)
    End If
End Function

Function FirstNonEmpty(values)
    FirstNonEmpty = ""

    Dim i
    Dim v
    For i = LBound(values) To UBound(values)
        v = Trim(CStr(values(i)))
        If v <> "" Then
            FirstNonEmpty = v
            Exit Function
        End If
    Next
End Function

Function IsReadableText(value)
    Dim s
    s = Trim(CStr(value))
    IsReadableText = False

    If s = "" Then Exit Function
    If UCase(s) = "NOT ACCESSIBLE" Then Exit Function
    If UCase(s) = "<EMPTY>" Then Exit Function
    If UCase(s) = "DIRECT=NOT ACCESSIBLE | PARAMETER=NOT ACCESSIBLE" Then Exit Function

    IsReadableText = True
End Function

Function YesNo(value)
    If CBool(value) Then
        YesNo = "Yes"
    Else
        YesNo = "No"
    End If
End Function

Function NormalizeName(value)
    Dim s
    s = UCase(CStr(value))
    s = Replace(s, " ", "")
    s = Replace(s, "_", "")
    s = Replace(s, "-", "")
    s = Replace(s, ".", "")
    s = Replace(s, "\", "")
    s = Replace(s, "/", "")
    s = Replace(s, "(", "")
    s = Replace(s, ")", "")
    NormalizeName = s
End Function

Function IsAutomationIdentifier(value)
    Dim s
    Dim i
    Dim ch

    s = CStr(value)
    If s = "" Then
        IsAutomationIdentifier = False
        Exit Function
    End If

    ch = Mid(s, 1, 1)
    If Not ((ch >= "A" And ch <= "Z") Or (ch >= "a" And ch <= "z") Or ch = "_") Then
        IsAutomationIdentifier = False
        Exit Function
    End If

    For i = 1 To Len(s)
        ch = Mid(s, i, 1)
        If Not ((ch >= "A" And ch <= "Z") Or (ch >= "a" And ch <= "z") Or _
                (ch >= "0" And ch <= "9") Or ch = "_") Then
            IsAutomationIdentifier = False
            Exit Function
        End If
    Next

    IsAutomationIdentifier = True
End Function

Function SafeDocumentName(doc)
    SafeDocumentName = ObjectName(doc)

    On Error Resume Next
    If SafeDocumentName = "" Then SafeDocumentName = CStr(doc.FullName)
    If Err.Number <> 0 Then
        Err.Clear
        SafeDocumentName = "<active document>"
    End If
    On Error GoTo 0
End Function

Function NewList()
    Set NewList = CreateObject("System.Collections.ArrayList")
End Function

Sub ListAdd(listObj, textValue)
    listObj.Add SafeText(textValue)
End Sub

Function WriteReportFile(doc, reportLines)
    Dim folderPath
    folderPath = ReportFolder(doc)

    Dim fso
    Set fso = CreateObject("Scripting.FileSystemObject")

    Dim reportPath
    reportPath = fso.BuildPath(folderPath, REPORT_FILE_NAME)

    Dim stream
    Set stream = Nothing

    On Error Resume Next
    Set stream = fso.CreateTextFile(reportPath, True, False)
    If Err.Number <> 0 Or stream Is Nothing Then
        Dim createErr
        createErr = Err.Description
        Err.Clear
        On Error GoTo 0
        WriteReportFile = WriteMinimalReportFile(doc, reportLines, "CreateTextFile", createErr)
        Exit Function
    End If

    Dim i
    For i = 0 To reportLines.Count - 1
        On Error Resume Next
        stream.WriteLine SafeText(reportLines.Item(i))
        If Err.Number <> 0 Then
            Err.Clear
            stream.WriteLine "<not writable> <WriteLine failed at report line " & CStr(i) & ">"
            If Err.Number <> 0 Then Err.Clear
        End If
        On Error GoTo 0
    Next

    On Error Resume Next
    stream.Close
    If Err.Number <> 0 Then Err.Clear
    On Error GoTo 0

    WriteReportFile = reportPath
End Function

Function WriteMinimalReportFile(doc, reportLines, errorLocation, errorDescription)
    Dim folderPath
    folderPath = ReportFolder(doc)

    Dim fso
    Set fso = CreateObject("Scripting.FileSystemObject")

    Dim reportPath
    reportPath = fso.BuildPath(folderPath, "selected_weld_design_object_probe_MINIMAL.txt")

    Dim stream
    Set stream = Nothing

    On Error Resume Next
    Set stream = fso.CreateTextFile(reportPath, True, False)
    If Err.Number <> 0 Or stream Is Nothing Then
        Err.Clear
        reportPath = fso.BuildPath(DesktopFolder(), "selected_weld_design_object_probe_MINIMAL.txt")
        Set stream = fso.CreateTextFile(reportPath, True, False)
    End If

    If Err.Number <> 0 Or stream Is Nothing Then
        Err.Clear
        On Error GoTo 0
        WriteMinimalReportFile = reportPath
        Exit Function
    End If

    stream.WriteLine "Selected object name: " & SafeText(ReportLineValue(reportLines, "Selected object name:"))
    If Err.Number <> 0 Then Err.Clear
    stream.WriteLine "TypeName: " & SafeText(ReportLineValue(reportLines, "TypeName:"))
    If Err.Number <> 0 Then Err.Clear
    stream.WriteLine "Parent path: " & SafeText(ReportLineValue(reportLines, "Parent path:"))
    If Err.Number <> 0 Then Err.Clear
    stream.WriteLine "Error location: " & SafeText(errorLocation)
    If Err.Number <> 0 Then Err.Clear
    stream.WriteLine "Error description: " & SafeText(errorDescription)
    If Err.Number <> 0 Then Err.Clear
    stream.Close
    If Err.Number <> 0 Then Err.Clear
    On Error GoTo 0

    WriteMinimalReportFile = reportPath
End Function

Function ReportLineValue(reportLines, prefix)
    ReportLineValue = "not available"

    If reportLines Is Nothing Then Exit Function

    Dim i
    Dim lineText
    Dim p
    p = CStr(prefix)

    On Error Resume Next
    For i = 0 To reportLines.Count - 1
        lineText = SafeText(reportLines.Item(i))
        If Left(lineText, Len(p)) = p Then
            ReportLineValue = Trim(Mid(lineText, Len(p) + 1))
            If ReportLineValue = "" Then ReportLineValue = "not available"
            Exit Function
        End If
        If Err.Number <> 0 Then Err.Clear
    Next
    On Error GoTo 0
End Function

Function SafeText(value)
    On Error Resume Next

    If IsNull(value) Then
        SafeText = "<Null>"
        Exit Function
    End If

    If IsEmpty(value) Then
        SafeText = "<Empty>"
        Exit Function
    End If

    Dim s
    s = CStr(value)

    If Err.Number <> 0 Then
        Err.Clear
        SafeText = "<CStr failed>"
        Exit Function
    End If

    s = Replace(s, Chr(0), "")
    s = Replace(s, vbCrLf, " ")
    s = Replace(s, vbCr, " ")
    s = Replace(s, vbLf, " ")

    If Len(s) > 2000 Then
        s = Left(s, 2000) & " ... <truncated>"
    End If

    SafeText = s
End Function

Function ReportFolder(doc)
    ReportFolder = ""

    On Error Resume Next
    ReportFolder = CStr(doc.Path)
    If Err.Number <> 0 Then
        Err.Clear
        ReportFolder = ""
    End If
    On Error GoTo 0

    If ReportFolder = "" Then ReportFolder = DesktopFolder()
End Function

Function DesktopFolder()
    On Error Resume Next
    DesktopFolder = CreateObject("WScript.Shell").SpecialFolders("Desktop")
    If Err.Number <> 0 Or DesktopFolder = "" Then
        Err.Clear
        DesktopFolder = CreateObject("Scripting.FileSystemObject").GetSpecialFolder(2)
    End If
    On Error GoTo 0
End Function
